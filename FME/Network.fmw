FME workspace Network.fmw

Parameters:
- omr = kommune   # Områdetype
- omrNvn = 403   # Område
- Inspire_fcName = TransportNetworks   # INSPIRE Feature Catalogue Name
- Gdf_fcName = GDF   # GDF Feature Catalogue Name
- gmlFolder = C:\DATA\GitHub\ITSGML\GML   # GML-hovedmappe
- DestDataset_GML = C:\DATA\GitHub\ITSGML\GML\Network.gml   # Destination Geography Markup Language (GML) File
- DestDataset_GML_3 = C:\DATA\GitHub\ITSGML\GML   # Destination Geography Markup Language (GML) File
- xsdName = network   # skjemanavn
- gmlNs = https://raw.githubusercontent.com/jetgeo/ITSGML/master/XSD   # GML Namespace
- namespace = vegvesen.no.nvdb   # Namespace
- nettverk:   # Python Script
      ns = FME_MacroValues['namespace'] + '.nw.' + FME_MacroValues['omr'] + '_' + FME_MacroValues['omrNvn']
      return ns

Writers:
- GML_1: GML to $(DestDataset_GML) in ETRS89.UTM-33N
- GML_2: GML to $(DestDataset_GML_3) in EPSG:6173

Creator
    GEOMTYPE = Geometry Object
    NUM = 1
    CREATED -> AttributeCreator
    CREATED -> AttributeManager_4
AttributeCreator
    ATTR_TABLE:
      SET_TO href = https://www.vegvesen.no/nvdb/api/v2/vegnett/lenker?$(omr)=$(omrNvn)&antall=5000

      SET_TO omrNvn = $(omrNvn)
      SET_TO omr = $(omr)
    -> NVDB_Vegnettleser [_Input]
Note: Lesing av XML for vegnett:
NVDB_Vegnettleser
    NESTE.HREF = @Value(href)
    OMR = $(omr)
    OMRNVN = $(omrNvn)
    namespace = vegvesen.no.nvdb
    nettverk:
      ns = FME_MacroValues['namespace'] + '.nw.' + FME_MacroValues['OMR'] + '_' + FME_MacroValues['OMRNVN']
      return ns
    Veglenkesekvens -> LinkSequence (writer GML_1)
    Veglenkesekvens -> AttributeManager_3
    Veglenke -> GeometryPropertySetter_2
    Veglenke -> AttributeManager_3
    Veglenke -> NVDB_Vegnettleser_Veglenke
    Vegnode -> GeometryPropertySetter
    Vegnode -> AttributeManager_3
    Vegnode -> NVDB_Vegnettleser_Vegnode
AttributeManager_3
    ATTR_TABLE = SET_TO xlink_href = #@Value(gml_id)
    -> ListBuilder
ListBuilder
    GROUPS_ORDERED = No
    LIST_ATTRS_TO_INCLUDE = xlink_href
    LIST_NAME = element
    -> AttributeManager_2
AttributeManager_2
    ATTR_TABLE:
      SET_TO fme_feature_type = Network
      SET_TO gml_id = $(namespace).nw.$(omr)_$(omrNvn)
    -> Network (writer GML_1)
Network (writer GML_1)
    attributes: geographicalName{} xml_xml, geographicalName{}.xsi_nil xml_boolean, element{}.nilReason xml_buffer, element{}.gml_remoteSchema xml_buffer, element{}.xlink_href xml_buffer, element{}.xlink_title xml_buffer, element{}.owns xml_boolean
NVDB_Vegnettleser_Veglenke: Inspector
LinkSequence (writer GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, link{}.DirectedLink.direction xml_char(1), link{}.DirectedLink.link.nilReason xml_buffer, link{}.DirectedLink.link.gml_remoteSchema xml_buffer, link{}.DirectedLink.link.xlink_href xml_buffer, link{}.DirectedLink.link.xlink_title xml_buffer, link{}.DirectedLink.link.owns xml_boolean
NVDB_Vegnettleser_Vegnode: Inspector
GeometryPropertySetter_2
    GEOM_NAME_FIELD = centrelineGeometry
    OVERWRITE_CHOICE = Yes
    SETTYPE_PARAM = Geometry Name
    SET -> AttributeManager
AttributeManager
    ATTR_TABLE:
      RENAME_SET_VALUE lenkesekvens.Lenkesekvensreferanse.startposisjon > startMeasure
      RENAME_SET_VALUE lenkesekvens.Lenkesekvensreferanse.sluttposisjon > endMeasure
      SET_TO startMeasure.uom = interpolative
      SET_TO endMeasure.uom = interpolative
    -> Link (writer GML_1)
    -> AttributeExposer_4
Link (writer GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, centrelineGeometry xml_geometry, startNode.owns xml_boolean, startNode.nilReason xml_buffer, startNode.gml_remoteSchema xml_buffer, startNode.xlink_href xml_buffer, startNode.xlink_title xml_buffer, endNode.owns xml_boolean, endNode.nilReason xml_buffer, endNode.gml_remoteSchema xml_buffer, endNode.xlink_href xml_buffer, endNode.xlink_title xml_buffer, startMeasure xml_real64, startMeasure.uom xml_buffer, endMeasure xml_real64, endMeasure.uom xml_buffer
AttributeExposer_4
    ATTR_LIST = startNode.xlink_href,endNode.xlink_href
    -> AttributeManager_10
AttributeManager_10
    ATTR_TABLE:
      SET_TO fme_feature_type = RoadElement
      SET_TO beginLifespanVersion = @Value(startdato)
      SET_TO typeName = @Value(fme_feature_type)
      SET_TO featureTypeReference.xlink_href = $(Gdf_fcName).gml#$(Gdf_fcName).@Value(fme_feature_type)
      SET_TO LinearLocationReference.networkReference{0}.SimpleLinearReference.applicableDirection = FME_CONDITIONAL:DEFAULT_VALUE'inOppositeDirection'BOOL_OP;OR;COMPOSITE_TEST;<Unused>;TEST @Value(endMeasure) >= @Value(startMeasure)'inDirection'FME_NUM_CONDITIONS2___
      SET_TO LinearLocationReference.networkReference{0}.SimpleLinearReference.fromPosition.LR_DistanceExpression.distanceAlong = @Value(startMeasure)
      SET_TO LinearLocationReference.networkReference{0}.SimpleLinearReference.toPosition.LR_DistanceExpression.distanceAlong = @Value(endMeasure)
      SET_TO LinearLocationReference.networkReference{0}.SimpleLinearReference.fromPosition.LR_DistanceExpression.distanceAlong.uom = interpolative
      SET_TO LinearLocationReference.networkReference{0}.SimpleLinearReference.toPosition.LR_DistanceExpression.distanceAlong.uom = interpolative
      SET_TO LinearLocationReference.networkReference{0}.SimpleLinearReference.element.xlink_href = Network.gml#vegvesen.no.nvdb.rls.@Value(lenkesekvens.Lenkesekvensreferanse.identifikasjon.Identifikasjon.lokalId)
      SET_TO property{0}.GenericFeatureProperty.memberName = startNode
      SET_TO property{0}.GenericFeatureProperty.propertyTypeReference.xlink_href = $(Gdf_fcName).gml#$(Gdf_fcName).AssociationRoles.Link.Node.startNode
      SET_TO property{0}.GenericFeatureProperty.propertyStructure = association
      SET_TO property{0}.GenericFeatureProperty.valueReference.xlink_href = @Value(startNode.xlink_href)
      SET_TO property{1}.GenericFeatureProperty.memberName = endNode
      SET_TO property{1}.GenericFeatureProperty.propertyTypeReference.xlink_href = $(Gdf_fcName).gml#$(Gdf_fcName).AssociationRoles.Link.Node.endNode
      SET_TO property{1}.GenericFeatureProperty.propertyStructure = association
      SET_TO property{1}.GenericFeatureProperty.valueReference.xlink_href = @Value(endNode.xlink_href)
    -> DateTimeConverter
    -> GeometryExtractor_3
GeometryExtractor_3
    ATTR = _refLinkGeometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> AttributeManager_14
GeometryPropertySetter
    GEOM_NAME_FIELD = geometry
    OVERWRITE_CHOICE = Yes
    SETTYPE_PARAM = Geometry Name
    SET -> Node (writer GML_1)
    SET -> AttributeManager_11
AttributeManager_11
    ATTR_TABLE:
      SET_TO fme_feature_type = Junction
      SET_TO typeName = @Value(fme_feature_type)
      SET_TO featureTypeReference.xlink_href = $(Gdf_fcName).gml#$(Gdf_fcName).@Value(fme_feature_type)
    -> DateTimeConverter
    -> GeometryExtractor_2
Node (writer GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, geometry xml_geometry
AttributeManager_4
    ATTR_TABLE = SET_TO ftIDs = 105;821;573;174
    -> AttributeSplitter
AttributeSplitter
    ATTR_NAME = ftIDs
    DELIMITER = ;
    DROP_EMPTY_PARTS = No
    LIST_NAME = _ftID
    TRIM_OPTION = Both
    -> ListExploder_2
ListExploder_2
    ATTR_ACCUM_MODE = Merge List Attributes
    ATTR_CONFLICT_RES = Use List Attribute Values
    INDEX_ATTR = _element_index
    LIST_ATTR = _ftID{}
    ELEMENTS -> AttributeCreator_2
AttributeCreator_2
    ATTR_TABLE = SET_TO href = https://www.vegvesen.no/nvdb/api/v2/vegobjekter/@Value(_ftID)?$(omr)=$(omrNvn)&antall=5000&inkluder=alle
    -> NVDB_Leser [_Input]
Note: Leser fagdata
NVDB_Leser
    NESTE.HREF = @Value(href)
    -> SchemaMapper
AttributeFilter
    ATTR_NAME = fme_feature_type
    ATTR_VALUES = <Empty>,<Missing>,<Null>,<Unfiltered>,Svingerestriksjon,Fartsgrense,Vegbredde,FunksjonellVegklasse,Gangfelt
    Svingerestriksjon -> ListIndexer_3
    Fartsgrense -> AttributeExposer_2
    Vegbredde -> AttributeExposer
    FunksjonellVegklasse -> AttributeExposer_6
    Gangfelt -> AttributeExposer_3
Snipper_4
    DEAGGREGATE_INPUT = YES
    ENDLOCATIONATTR = 20
    MEASUREMENTTYPE = 2D
    SNIPMODE = Distance (Value)
    STARTLOCATIONATTR = 0
    -> Snipper_Output_4
Snipper_Output_4: Inspector
Snipper_3
    DEAGGREGATE_INPUT = YES
    ENDLOCATIONATTR = 20
    MEASUREMENTTYPE = 2D
    SNIPMODE = Distance (Value)
    STARTLOCATIONATTR = -1
    -> Snipper_Output_3
Snipper_Output_3: Inspector
FeatureMerger
    ATTR_ACCUM_MODE = Merge Supplier
    ATTR_CONFLICT_RES = Use Requestor
    IGNORE_NULLS = No
    JOIN_KEYS = @Value(gml_id) @Value(restr_gml_id) AUTO
    MERGE_TYPE = Attributes Only
    PROCESS_DUPS = NO
    REJECT_NULL_MISSING_KEYS = No
    SUPPLIERS_FIRST = No
    MERGED -> AttributeManager_18
AttributeManager_18
    ATTR_TABLE:
      SET_TO fme_feature_type = ProhibitedManoeuvre
      SET_TO beginLifespanVersion = @Value(startdato)
      SET_TO typeName = @Value(fme_feature_type)
      SET_TO featureTypeReference.xlink_href = $(Gdf_fcName).gml#$(Gdf_fcName).@Value(fme_feature_type)
      SET_TO property{0}.GenericFeatureProperty.memberName = firstRoadElement
      SET_TO property{0}.GenericFeatureProperty.propertyTypeReference.xlink_href = $(Gdf_fcName).gml#$(Gdf_fcName).AssociationRoles.Manoeuvre.RoadElement.firstRoadElement
      SET_TO property{0}.GenericFeatureProperty.propertyStructure = association
      SET_TO property{0}.GenericFeatureProperty.valueReference.xlink_href = Network.gml#@Value(firstRL.rl_gml_id)
      SET_TO property{1}.GenericFeatureProperty.memberName = secondRoadElement
      SET_TO property{1}.GenericFeatureProperty.propertyTypeReference.xlink_href = $(Gdf_fcName).gml#$(Gdf_fcName).AssociationRoles.Manoeuvre.RoadElement.secondRoadElement
      SET_TO property{1}.GenericFeatureProperty.propertyStructure = association
      SET_TO property{1}.GenericFeatureProperty.valueReference.xlink_href = Network.gml#@Value(secondRL.rl_gml_id)
      SET_TO property{2}.GenericFeatureProperty.memberName = junction
      SET_TO property{2}.GenericFeatureProperty.propertyTypeReference.xlink_href = $(Gdf_fcName).gml#$(Gdf_fcName).AssociationRoles.Manoeuvre.Junction.junction
      SET_TO property{2}.GenericFeatureProperty.propertyStructure = association
      SET_TO property{2}.GenericFeatureProperty.valueReference.xlink_href = Network.gml#@Value(node_gml_id)
    -> GeometryReplacer
    -> AttributeManager_18_Output
AttributeManager_18_Output: Inspector
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_linkGeometry)
    SRS_AXIS_ORDER_DISPLAY = Automatic
    -> DateTimeConverter
TestFilter_5
    DEFAULT_VALUE = endInNode
    TEST_LIST = "BOOL_OP,OR,COMPOSITE_TEST,""""""<Unused>"""""",TEST_CLAUSE,TEST @Value(secondRL.startnodeId) = @Value(node_id)",startInNode
    startInNode -> TestFilter_5_startInNode
    startInNode -> Snipper_2
    endInNode -> TestFilter_5_endInNode
    endInNode -> Snipper
TestFilter_5_startInNode: Inspector
TestFilter_5_endInNode: Inspector
Snipper_2
    DEAGGREGATE_INPUT = YES
    ENDLOCATIONATTR = 20
    MEASUREMENTTYPE = 2D
    SNIPMODE = Distance (Value)
    STARTLOCATIONATTR = 0
    -> Snipper_Output_2
Snipper_Output_2: Inspector
Snipper
    DEAGGREGATE_INPUT = YES
    ENDLOCATIONATTR = 20
    MEASUREMENTTYPE = 2D
    SNIPMODE = Distance (Value)
    STARTLOCATIONATTR = -1
    -> Snipper_Output
Snipper_Output: Inspector
Feature (writer GML_2)
    attributes: validFrom xml_date, validTo xml_date, beginLifespanVersion xml_datetime, endLifespanVersion xml_datetime, featureTypeReference.nilReason xml_buffer, featureTypeReference.gml_remoteSchema xml_buffer, featureTypeReference.xlink_href xml_buffer, featureTypeReference.xlink_title xml_buffer, featureTypeReference.owns xml_boolean, locationReference{}.AgoraLocationReference.base64String xml_buffer, locationReference{}.AgoraLocationReference.agoraBinaryVersion xml_buffer, locationReference{}.AgoraLocationReference.agoraBinaryVersion.codeSpace xml_buffer, locationReference{}.GeometryLocationReference.encodedGeometry xml_geometry, locationReference{}.LinearLocationReference.name xml_buffer, locationReference{}.LinearLocationReference.description xml_buffer, locationReference{}.LinearLocationReference.networkReference{}.LinkReference.overridingLRM xml_xml, locationReference{}.LinearLocationReference.networkReference{}.LinkReference.element.nilReason xml_buffer, locationReference{}.LinearLocationReference.networkReference{}.LinkReference.element.gml_remoteSchema xml_buffer, locationReference{}.LinearLocationReference.networkReference{}.LinkReference.element.xlink_href xml_buffer, locationReference{}.LinearLocationReference.networkReference{}.LinkReference.element.xlink_title xml_buffer, locationReference{}.LinearLocationReference.networkReference{}.LinkReference.element.owns xml_boolean, locationReference{}.LinearLocationReference.networkReference{}.SimpleLinearReference.overridingLRM xml_xml, locationReference{}.LinearLocationReference.networkReference{}.SimpleLinearReference.element.nilReason xml_buffer, locationReference{}.LinearLocationReference.networkReference{}.SimpleLinearReference.element.gml_remoteSchema xml_buffer, locationReference{}.LinearLocationReference.networkReference{}.SimpleLinearReference.element.xlink_href xml_buffer, locationReference{}.LinearLocationReference.networkReference{}.SimpleLinearReference.element.xlink_title xml_buffer, locationReference{}.LinearLocationReference.networkReference{}.SimpleLinearReference.element.owns xml_boolean, locationReference{}.LinearLocationReference.networkReference{}.SimpleLinearReference.fromPosition.LR_DistanceExpression.distanceAlong xml_real64, locationReference{}.LinearLocationReference.networkReference{}.SimpleLinearReference.fromPosition.LR_DistanceExpression.distanceAlong.uom xml_buffer, locationReference{}.LinearLocationReference.networkReference{}.SimpleLinearReference.toPosition.LR_DistanceExpression.distanceAlong xml_real64,
      locationReference{}.LinearLocationReference.networkReference{}.SimpleLinearReference.toPosition.LR_DistanceExpression.distanceAlong.uom xml_buffer, locationReference{}.LinearLocationReference.networkReference{}.SimplePointReference.overridingLRM xml_xml, locationReference{}.LinearLocationReference.networkReference{}.SimplePointReference.element.nilReason xml_buffer, locationReference{}.LinearLocationReference.networkReference{}.SimplePointReference.element.gml_remoteSchema xml_buffer, locationReference{}.LinearLocationReference.networkReference{}.SimplePointReference.element.xlink_href xml_buffer, locationReference{}.LinearLocationReference.networkReference{}.SimplePointReference.element.xlink_title xml_buffer, locationReference{}.LinearLocationReference.networkReference{}.SimplePointReference.element.owns xml_boolean, locationReference{}.LinearLocationReference.networkReference{}.SimplePointReference.atPosition.LR_DistanceExpression.distanceAlong xml_real64, locationReference{}.LinearLocationReference.networkReference{}.SimplePointReference.atPosition.LR_DistanceExpression.distanceAlong.uom xml_buffer, locationReference{}.LinearLocationReference.networkReference{}.NetworkReference.overridingLRM xml_xml, locationReference{}.LinearLocationReference.networkReference{}.NetworkReference.element.nilReason xml_buffer, locationReference{}.LinearLocationReference.networkReference{}.NetworkReference.element.gml_remoteSchema xml_buffer, locationReference{}.LinearLocationReference.networkReference{}.NetworkReference.element.xlink_href xml_buffer, locationReference{}.LinearLocationReference.networkReference{}.NetworkReference.element.xlink_title xml_buffer, locationReference{}.LinearLocationReference.networkReference{}.NetworkReference.element.owns xml_boolean, locationReference{}.LocationByExternalReference.predefinedLocationReference xml_buffer, locationReference{}.LocationByExternalReference.predefinedLocationReference.codeSpace xml_buffer, locationReference{}.OpenLRLocationReference.binaryLocationReference.BinaryLocationReference.base64String xml_buffer, locationReference{}.OpenLRLocationReference.binaryLocationReference.BinaryLocationReference.openLRBinaryVersion xml_buffer, locationReference{}.OpenLRLocationReference.binaryLocationReference.BinaryLocationReference.openLRBinaryVersion.codeSpace xml_buffer, typeName xml_buffer, typeName.codeSpace xml_buffer, locationReference{}.LinearLocationReference.networkReference{}.LinkReference.applicableDirection xml_buffer, locationReference{}.LinearLocationReference.networkReference{}.SimpleLinearReference.applicableDirection xml_buffer, locationReference{}.LinearLocationReference.networkReference{}.SimplePointReference.applicableDirection xml_buffer, property{}.GenericFeatureProperty.memberName xml_buffer, property{}.GenericFeatureProperty.memberName.codeSpace xml_buffer, property{}.GenericFeatureProperty.propertyStructure xml_buffer, property{}.GenericFeatureProperty.propertyTypeReference.nilReason xml_buffer, property{}.GenericFeatureProperty.propertyTypeReference.gml_remoteSchema xml_buffer,
      property{}.GenericFeatureProperty.propertyTypeReference.xlink_href xml_buffer, property{}.GenericFeatureProperty.propertyTypeReference.xlink_title xml_buffer, property{}.GenericFeatureProperty.propertyTypeReference.owns xml_boolean, property{}.GenericFeatureProperty.value xml_buffer, property{}.GenericFeatureProperty.unitOfMeasure xml_buffer, property{}.GenericFeatureProperty.subproperty{}.GenericFeatureProperty xml_xml, beginLifespanVersion.xsi_nil xml_boolean, validFrom.xsi_nil xml_boolean, property{}.GenericFeatureProperty.valueReference.owns xml_boolean, property{}.GenericFeatureProperty.valueReference.nilReason xml_buffer, property{}.GenericFeatureProperty.valueReference.gml_remoteSchema xml_buffer, property{}.GenericFeatureProperty.valueReference.xlink_href xml_buffer, property{}.GenericFeatureProperty.valueReference.xlink_title xml_buffer

Bookmark: Finner node som restriksjonen går gjennom
AttributeManager_14
    ATTR_TABLE:
      RENAME_SET_VALUE gml_id > rl_gml_id
      RENAME_SET_VALUE veglenkeid > rls_id
      RENAME_SET_VALUE startNode.xlink_href > startNode_xlink_href
      RENAME_SET_VALUE endNode.xlink_href > endNode_xlink_href
    -> AttributeKeeper_2
    -> AttributeKeeper_3
AttributeKeeper_2
    KEEP_ATTRS = startMeasure,sluttnodeId,_refLinkGeometry,endMeasure,rl_gml_id,rls_id,startnodeId
    -> AttributeManager_16
AttributeManager_16
    ATTR_TABLE = SET_TO node_id = @Value(startnodeId)
    -> FeatureMerger_5 [SUPPLIER]
AttributeKeeper_3
    KEEP_ATTRS = startMeasure,sluttnodeId,_refLinkGeometry,endMeasure,rl_gml_id,rls_id,startnodeId
    -> AttributeManager_17
AttributeManager_17
    ATTR_TABLE = SET_TO node_id = @Value(sluttnodeId)
    -> FeatureMerger_5 [SUPPLIER]
GeometryExtractor_2
    ATTR = _nodeGeometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> SpatialRelator [Supplier]
AttributeManager_15
    ATTR_TABLE:
      RENAME_SET_VALUE gml_id > restr_gml_id
      RENAME_SET_VALUE firstRoadElement.SimpleLinearReference.element.xlink_href > firstRoadElement_xlink_href
      RENAME_SET_VALUE firstRoadElement.SimpleLinearReference.fromPosition.LR_DistanceExpression.distanceAlong > firstRoadElement_fromPosition
      RENAME_SET_VALUE firstRoadElement.SimpleLinearReference.toPosition.LR_DistanceExpression.distanceAlong > firstRoadElement_toPosition
      RENAME_SET_VALUE secondRoadElement.SimpleLinearReference.element.xlink_href > secondRoadElement_xlink_href
      RENAME_SET_VALUE secondRoadElement.SimpleLinearReference.fromPosition.LR_DistanceExpression.distanceAlong > secondRoadElement_fromPosition
      RENAME_SET_VALUE secondRoadElement.SimpleLinearReference.toPosition.LR_DistanceExpression.distanceAlong > secondRoadElement_toPosition
      RENAME_SET_VALUE firstRoadElement.SimpleLinearReference.lenkesekvens.Identifikasjon.lokalId > firstRoadElement_rls_id
      RENAME_SET_VALUE secondRoadElement.SimpleLinearReference.lenkesekvens.Identifikasjon.lokalId > secondRoadElement_rls_id
    -> AttributeKeeper
AttributeKeeper
    KEEP_ATTRS = firstRoadElement_fromPosition,firstRoadElement_toPosition,secondRoadElement_rls_id,restr_gml_id,secondRoadElement_toPosition,firstRoadElement_rls_id,secondRoadElement_fromPosition
    -> Bufferer
Bufferer
    ANGLE = 22.5
    CAP_STYLE = Round
    CORNER_STYLE = Round
    MODE = AREA
    OFFSET = 15
    BUFFERED -> SpatialRelator [Requestor]
Note: Finn nærliggende noder
SpatialRelator
    AGGREGATE_HANDLING = Yes
    CALC_CARD = No
    CURVE_BOUNDARY_RULE_PARAM = Default Rule
    LIST_NAME = RelatedNodes
    PREDICATES = INTERSECTS
    SUCCESS_ATTR = _related_candidates
    -> ListExploder_5
ListExploder_5
    ATTR_ACCUM_MODE = Merge List Attributes
    ATTR_CONFLICT_RES = Use List Attribute Values
    INDEX_ATTR = _element_index
    LIST_ATTR = RelatedNodes{}
    ELEMENTS -> FeatureMerger_5 [REQUESTOR]
Note: Alle nærliggende noder med lenker som er knytta til hver node
FeatureMerger_5
    ATTR_ACCUM_MODE = Merge Supplier
    ATTR_CONFLICT_RES = Use Requestor
    IGNORE_NULLS = No
    JOIN_KEYS = @Value(identifikasjon.Identifikasjon.lokalId) @Value(node_id) AUTO
    LIST_ATTRS_TO_INCLUDE = _refLinkGeometry endMeasure rl_gml_id rls_id startMeasure sluttnodeId startnodeId
    LIST_NAME = linkList
    MERGE_TYPE = Attributes Only
    PROCESS_DUPS = NO
    REJECT_NULL_MISSING_KEYS = No
    SUPPLIERS_FIRST = No
    MERGED -> ListSearcher
ListSearcher
    ATTR_VALUE = @Value(firstRoadElement_rls_id)
    INDEX_ATTR = _list_index
    LIST_ATTR = linkList{}.rls_id
    SEARCH_TYPE = First exact match
    FOUND -> ListSearcher_2
Note: Noder med begge lenker tilhørende restriksjonen
ListSearcher_2
    ATTR_VALUE = @Value(secondRoadElement_rls_id)
    INDEX_ATTR = _list_index
    LIST_ATTR = linkList{}.rls_id
    SEARCH_TYPE = First exact match
    FOUND -> AttributeManager_12
AttributeManager_12
    ATTR_TABLE = RENAME_SET_VALUE gml_id > node_gml_id
    -> ListExploder

Bookmark: Oversetter til GML-verdier og -navn
Note: Oversetter tillatte verdier til GML-verdier
SchemaMapper
    CSV2_CASE_SENSITIVE_FIELD_NAMES = Yes
    CSV2_DATA_START_LINE = 2
    CSV2_DELIMITER = ;
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = C:\DATA\GitHub\NVDBGML\XSD\NVDB_enMapping.csv
    FORMAT = CSV2
    IDXDESTATTR = fme_feature_type
    IDXDESTCOL = ""
    IDXSOURCEATTR = fme_feature_type
    IDXSOURCECOL = ""
    MAP_ATTRS = """""" ptid name
    MATCH_ATTRS = ptid enid
    ROW_ID_ATTR = _schemamapper_row_ids
    TABLE = CSV
    MAPPED -> SchemaMapper_2
    UNMAPPED -> SchemaMapper_2
Note: Oversetter egenskapsnavn til GML-navn
SchemaMapper_2
    CSV2_CASE_SENSITIVE_FIELD_NAMES = Yes
    CSV2_DATA_START_LINE = 2
    CSV2_DELIMITER = ;
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = C:\DATA\GitHub\NVDBGML\XSD\NVDB_ptMapping.csv
    FORMAT = CSV2
    IDXDESTATTR = fme_feature_type
    IDXDESTCOL = ""
    IDXSOURCEATTR = fme_feature_type
    IDXSOURCECOL = ""
    MAP_ATTRS = ptid name """"""
    MATCH_ATTRS = ft_attr ftid
    ROW_ID_ATTR = _schemamapper_row_ids
    TABLE = CSV
    MAPPED -> NullAttributeMapper_3
    UNMAPPED -> NullAttributeMapper_3
NullAttributeMapper_3
    ATTRCHOICE = All Attributes
    NULL_TREATMENT = Missing
    SOURCE_ATTR_VAL = Empty Null
    -> SchemaMapper_3
Note: Oversetter objekttypenavn til GML-navn
SchemaMapper_3
    CSV2_CASE_SENSITIVE_FIELD_NAMES = Yes
    CSV2_DATA_START_LINE = 2
    CSV2_DELIMITER = ;
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = C:\DATA\GitHub\NVDBGML\XSD\NVDB_ftMapping.csv
    FORMAT = CSV2
    IDXDESTATTR = fme_feature_type
    IDXDESTCOL = name
    IDXSOURCEATTR = fme_feature_type
    IDXSOURCECOL = ftid
    ROW_ID_ATTR = _schemamapper_row_ids
    TABLE = CSV
    MAPPED -> AttributeFilter

Bookmark: GDF-mapping Svingerestriksjon --> ProhibitedManoeuvre
Note: First road element
ListIndexer_3
    INDEX = 0
    LIST_ATTR = LinearLocationReference.networkReference{}
    PREFIX = firstRoadElement.
    -> ListIndexer_4
Note: Second road element
ListIndexer_4
    INDEX = 1
    LIST_ATTR = LinearLocationReference.networkReference{}
    PREFIX = secondRoadElement.
    -> AttributeRemover_3
AttributeRemover_3
    LIST_ATTRS = LinearLocationReference.networkReference{} LinearLocationReference.networkReference{}.SimpleLinearReference.applicableDirection LinearLocationReference.networkReference{}.SimpleLinearReference.element.xlink_href LinearLocationReference.networkReference{}.SimpleLinearReference.fromPosition.LR_DistanceExpression.distanceAlong LinearLocationReference.networkReference{}.SimpleLinearReference.fromPosition.LR_DistanceExpression.distanceAlong.uom LinearLocationReference.networkReference{}.SimpleLinearReference.toPosition.LR_DistanceExpression.distanceAlong LinearLocationReference.networkReference{}.SimpleLinearReference.toPosition.LR_DistanceExpression.distanceAlong.uom LinearLocationReference.networkReference{}.SimplePointReference.applicableDirection LinearLocationReference.networkReference{}.SimplePointReference.atPosition.LR_DistanceExpression.distanceAlong LinearLocationReference.networkReference{}.SimplePointReference.atPosition.LR_DistanceExpression.distanceAlong.uom LinearLocationReference.networkReference{}.SimplePointReference.element.xlink_href
    -> AttributeExposer_5
    -> FeatureMerger [REQUESTOR]
AttributeExposer_5
    ATTR_LIST = firstRoadElement.SimpleLinearReference.lenkesekvens.Identifikasjon.lokalId,firstRoadElement.SimpleLinearReference.toPosition.LR_DistanceExpression.distanceAlong,secondRoadElement.SimpleLinearReference.lenkesekvens.Identifikasjon.lokalId,secondRoadElement.SimpleLinearReference.toPosition.LR_DistanceExpression.distanceAlong
    -> AttributeManager_15

Bookmark: Finner berørt lenke, eller den som ligger nærmest i tilfelle posisjonen ikke er på en lenke som tilhører noden
ListExploder
    ATTR_ACCUM_MODE = Merge List Attributes
    ATTR_CONFLICT_RES = Use List Attribute Values
    INDEX_ATTR = _element_index
    LIST_ATTR = linkList{}
    ELEMENTS -> TestFilter_2
    ELEMENTS -> TestFilter_3
TestFilter_2
    DEFAULT_VALUE = <UNFILTERED>
    TEST_LIST = "BOOL_OP,OR,COMPOSITE_TEST,""""""<Unused>"""""",TEST_CLAUSE,TEST @Value(firstRoadElement_rls_id) = @Value(rls_id)",firstRLS
    firstRLS -> AttributeManager_19
AttributeManager_19
    ATTR_TABLE = SET_TO distance = FME_CONDITIONAL:DEFAULT_VALUE'@abs(@Value(firstRoadElement_toPosition)-@Value(endMeasure))'BOOL_OP;AND;COMPOSITE_TEST;<Unused>;TEST @Value(startMeasure) <= @Value(firstRoadElement_toPosition);TEST @Value(endMeasure) >= @Value(firstRoadElement_fromPosition)'0'BOOL_OP;OR;COMPOSITE_TEST;<Unused>;TEST @abs(@Value(startMeasure)-@Value(firstRoadElement_fromPosition)) < @abs(@Value(firstRoadElement_toPosition)-@Value(endMeasure))'@abs(@Value(startMeasure)-@Value(firstRoadElement_fromPosition))'FME_NUM_CONDITIONS3___
    -> ListBuilder_2
ListBuilder_2
    GROUPS_ORDERED = No
    GROUP_BY = _nodeGeometry restr_gml_id node_id node_gml_id
    LIST_ATTRS_TO_INCLUDE = _refLinkGeometry distance rl_gml_id sluttnodeId startnodeId
    LIST_NAME = _firstRlList
    -> ListSorter
ListSorter
    ORDER = Ascending
    SRC_LIST = _firstRlList{}.distance
    TYPE = Numeric
    -> ListIndexer
ListIndexer
    INDEX = 0
    LIST_ATTR = _firstRlList{}
    PREFIX = firstRL.
    -> FeatureMerger_2 [REQUESTOR]
TestFilter_3
    DEFAULT_VALUE = <UNFILTERED>
    TEST_LIST = "BOOL_OP,OR,COMPOSITE_TEST,""""""<Unused>"""""",TEST_CLAUSE,TEST @Value(secondRoadElement_rls_id) = @Value(rls_id)",secondRLS
    secondRLS -> AttributeManager_20
AttributeManager_20
    ATTR_TABLE = SET_TO distance = FME_CONDITIONAL:DEFAULT_VALUE'@abs(@Value(secondRoadElement_toPosition)-@Value(endMeasure))'BOOL_OP;AND;COMPOSITE_TEST;<Unused>;TEST @Value(startMeasure) <= @Value(secondRoadElement_toPosition);TEST @Value(endMeasure) >= @Value(secondRoadElement_fromPosition)'0'BOOL_OP;OR;COMPOSITE_TEST;<Unused>;TEST @abs(@Value(startMeasure)-@Value(secondRoadElement_fromPosition)) < @abs(@Value(secondRoadElement_toPosition)-@Value(endMeasure))'@abs(@Value(startMeasure)-@Value(secondRoadElement_fromPosition))'FME_NUM_CONDITIONS3___
    -> ListBuilder_3
ListBuilder_3
    GROUPS_ORDERED = No
    GROUP_BY = _nodeGeometry restr_gml_id node_id node_gml_id
    LIST_ATTRS_TO_INCLUDE = _refLinkGeometry distance rl_gml_id sluttnodeId startnodeId
    LIST_NAME = _secondRlList
    -> ListSorter_2
ListSorter_2
    ORDER = Ascending
    SRC_LIST = _secondRlList{}.distance
    TYPE = Numeric
    -> ListIndexer_2
ListIndexer_2
    INDEX = 0
    LIST_ATTR = _secondRlList{}
    PREFIX = secondRL.
    -> FeatureMerger_2 [SUPPLIER]
FeatureMerger_2
    ATTR_ACCUM_MODE = Merge Supplier
    ATTR_CONFLICT_RES = Use Requestor
    IGNORE_NULLS = No
    JOIN_KEYS = @Value(restr_gml_id) @Value(restr_gml_id) AUTO
    MERGE_TYPE = Attributes Only
    PROCESS_DUPS = NO
    REJECT_NULL_MISSING_KEYS = No
    SUPPLIERS_FIRST = No
    MERGED -> GeometryReplacer_2
    MERGED -> GeometryReplacer_3

Bookmark: Lager ny geometri bestående av de to lenkene
GeometryReplacer_2
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(firstRL._refLinkGeometry)
    SRS_AXIS_ORDER_DISPLAY = Automatic
    -> TestFilter_4
    -> LineCombiner
TestFilter_4
    DEFAULT_VALUE = endInNode
    TEST_LIST = "BOOL_OP,OR,COMPOSITE_TEST,""""""<Unused>"""""",TEST_CLAUSE,TEST @Value(firstRL.startnodeId) = @Value(node_id)",startInNode
    startInNode -> TestFilter_4_startInNode
    startInNode -> Snipper_4
    endInNode -> TestFilter_4_endInNode
    endInNode -> Snipper_3
TestFilter_4_startInNode: Inspector
TestFilter_4_endInNode: Inspector
GeometryReplacer_3
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(secondRL._refLinkGeometry)
    SRS_AXIS_ORDER_DISPLAY = Automatic
    -> LineCombiner
    -> TestFilter_5
LineCombiner
    ACCUM_ATTRS_NAME = Use Attributes From One Feature
    BREAK = no
    BREAK_CONNECTION_ACROSS_SETS = Yes
    CONNECT_Z_MODE = First Wins
    CONSIDER_NODE_ELEVATION = no
    DEAGGREGATE_GEOMETRY = Deaggregate
    GROUP_BY = restr_gml_id
    LINES_AS_SEGMENTS = No
    PRESERVE = no
    TOPOLOGY = End noded
    LINE -> GeometryExtractor_4
GeometryExtractor_4
    ATTR = _linkGeometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> FeatureMerger [SUPPLIER]

Bookmark: INSPIRE-mapping
AttributeExposer_2
    ATTR_LIST = fme_feature_type,fartsgrenseVerdi
    -> AttributeManager_6
AttributeManager_6
    ATTR_TABLE:
      SET_TO fme_feature_type = SpeedLimit
      SET_TO property{0}.GenericFeatureProperty.memberName = speedLimitMinMaxType
      SET_TO property{0}.GenericFeatureProperty.propertyTypeReference.xlink_href = $(Inspire_fcName).gml#$(Inspire_fcName).@Value(fme_feature_type).speedLimitMinMaxType
      SET_TO property{0}.GenericFeatureProperty.propertyStructure = listedValue
      SET_TO property{0}.GenericFeatureProperty.valueReference.xlink_href = $(Inspire_fcName).gml#$(Inspire_fcName).SpeedLimitMinMaxValue.maximum
      SET_TO property{1}.GenericFeatureProperty.memberName = speedLimitValue
      SET_TO property{1}.GenericFeatureProperty.propertyTypeReference.xlink_href = $(Inspire_fcName).gml#$(Inspire_fcName).@Value(fme_feature_type).speedLimitValue
      SET_TO property{1}.GenericFeatureProperty.propertyStructure = simple
      SET_TO property{1}.GenericFeatureProperty.value = @Value(fartsgrenseVerdi)
      SET_TO property{1}.GenericFeatureProperty.unitOfMeasure = km/h
    -> AttributeManager_5
AttributeExposer
    ATTR_LIST = fme_feature_type,dekkebredde,vegbredde_Totalt,kjørebanebredde
    -> AttributeManager_7
AttributeManager_7
    ATTR_TABLE:
      SET_TO fme_feature_type = RoadWidth
      SET_TO property{0}.GenericFeatureProperty.memberName = width
      SET_TO property{0}.GenericFeatureProperty.propertyTypeReference.xlink_href = $(Inspire_fcName).gml#$(Inspire_fcName).@Value(fme_feature_type).width
      SET_TO property{0}.GenericFeatureProperty.propertyStructure = simple
      SET_TO property{0}.GenericFeatureProperty.value = FME_CONDITIONAL:DEFAULT_VALUE'_FME_NO_OP_'BOOL_OP;OR;COMPOSITE_TEST;<Unused>;TEST dekkebredde ATTRIBUTE_HAS_A_VALUE _FME_BLANK_STRING_'@Value(dekkebredde)'BOOL_OP;OR;COMPOSITE_TEST;<Unused>;TEST kjørebanebredde ATTRIBUTE_HAS_A_VALUE _FME_BLANK_STRING_'@Value(kjørebanebredde)'FME_NUM_CONDITIONS3___
      SET_TO property{0}.GenericFeatureProperty.unitOfMeasure = m
      SET_TO property{1}.GenericFeatureProperty.memberName = measuredRoadPart
      SET_TO property{1}.GenericFeatureProperty.propertyTypeReference.xlink_href = $(Inspire_fcName).gml#$(Inspire_fcName).@Value(fme_feature_type).measuredRoadPart
      SET_TO property{1}.GenericFeatureProperty.propertyStructure = simple
      SET_TO property{1}.GenericFeatureProperty.value = FME_CONDITIONAL:DEFAULT_VALUE'_FME_NO_OP_'BOOL_OP;OR;COMPOSITE_TEST;<Unused>;TEST dekkebredde ATTRIBUTE_HAS_A_VALUE _FME_BLANK_STRING_'pavedSurface'BOOL_OP;OR;COMPOSITE_TEST;<Unused>;TEST kjørebanebredde ATTRIBUTE_HAS_A_VALUE _FME_BLANK_STRING_'carriageway'FME_NUM_CONDITIONS3___
    -> AttributeManager_5
AttributeExposer_6
    ATTR_LIST = fme_feature_type,vegklasse
    -> AttributeValueMapper
AttributeValueMapper
    DIRECTION = Forward (Source To Destination)
    LUT = 0,mainRoad,1,firstClass,2,secondClass,3,thirdClass,4,fourthClass,5,fifthClass,6,sixthClass,7,seventhClass,8,eigthClass,9,ninthClass
    SRC = vegklasse
    VAL_ATTR = functionalClass
    -> AttributeManager_13
AttributeManager_13
    ATTR_TABLE:
      SET_TO fme_feature_type = FunctionalRoadClass
      SET_TO property{0}.GenericFeatureProperty.memberName = functionalClass
      SET_TO property{0}.GenericFeatureProperty.propertyTypeReference.xlink_href = $(Inspire_fcName).gml#$(Inspire_fcName).@Value(fme_feature_type).functionalClass
      SET_TO property{0}.GenericFeatureProperty.propertyStructure = listedValue
      SET_TO property{0}.GenericFeatureProperty.valueReference.xlink_href = $(Inspire_fcName).gml#$(Inspire_fcName).FunctionalRoadClassValue.@Value(functionalClass)
    -> AttributeManager_5
AttributeManager_5
    ATTR_TABLE:
      RENAME_SET_VALUE startdato > validFrom
      SET_TO beginLifespanVersion = @Value(validFrom)
      SET_TO typeName = @Value(fme_feature_type)
      SET_TO featureTypeReference.xlink_href = $(Inspire_fcName).gml#$(Inspire_fcName).@Value(fme_feature_type)
    -> DateTimeConverter

Bookmark: GDF-mapping Gangfelt --> PedestrianCrossing
AttributeExposer_3
    ATTR_LIST = fme_feature_type,markeringAvStriper,skiltet,belysningGangfelt,lysregulert,trafikkøy
    -> AttributeManager_8
AttributeManager_8
    ATTR_TABLE:
      SET_TO fme_feature_type = PedestrianCrossing
      SET_TO property{0}.GenericFeatureProperty.memberName = priority
      SET_TO property{0}.GenericFeatureProperty.propertyTypeReference.xlink_href = $(Gdf_fcName).gml#$(Gdf_fcName).@Value(fme_feature_type).priority
      SET_TO property{0}.GenericFeatureProperty.propertyStructure = listedValue
      SET_TO property{0}.GenericFeatureProperty.valueReference.xlink_href = FME_CONDITIONAL:DEFAULT_VALUE'GDF.gml#GDF.PedestrianCrossingPriority.pedestriansOverRoadTraffic'BOOL_OP;OR;COMPOSITE_TEST;<Unused>;TEST @Value(lysregulert) = ja'GDF.gml#GDF.PedestrianCrossingPriority.pedestriansOverRoadTrafficOnRequest'FME_NUM_CONDITIONS2___
      SET_TO property{1}.GenericFeatureProperty.memberName = signage
      SET_TO property{1}.GenericFeatureProperty.propertyTypeReference.xlink_href = $(Gdf_fcName).gml#$(Gdf_fcName).@Value(fme_feature_type).signage
      SET_TO property{1}.GenericFeatureProperty.propertyStructure = listedValue
      SET_TO property{1}.GenericFeatureProperty.valueReference.xlink_href = FME_CONDITIONAL:DEFAULT_VALUE'_FME_NO_OP_'BOOL_OP;OR;COMPOSITE_TEST;<Unused>;TEST @Value(lysregulert) = ja'GDF.gml#GDF.PedestrianCrossingSignage.trafficLightRegulated'BOOL_OP;AND;COMPOSITE_TEST;<Unused>;TEST @Value(skiltet) = ja;TEST @Value(lysregulert) = nei'GDF.gml#GDF.PedestrianCrossingSignage.passiveTrafficSigns'BOOL_OP;OR;COMPOSITE_TEST;<Unused>;TEST @Value(skiltet) = nei'GDF.gml#GDF.PedestrianCrossingSignage.noTrafficSigns'FME_NUM_CONDITIONS4___
      SET_TO property{2}.GenericFeatureProperty.memberName = type
      SET_TO property{2}.GenericFeatureProperty.propertyTypeReference.xlink_href = $(Gdf_fcName).gml#$(Gdf_fcName).@Value(fme_feature_type).type
      SET_TO property{2}.GenericFeatureProperty.propertyStructure = listedValue
      SET_TO property{2}.GenericFeatureProperty.valueReference.xlink_href = FME_CONDITIONAL:DEFAULT_VALUE'GDF.gml#GDF.PedestrianCrossingType.otherType'BOOL_OP;OR;COMPOSITE_TEST;<Unused>;TEST @Value(markeringAvStriper) = ikkeStriper'GDF.gml#GDF.PedestrianCrossingType.noRoadMarkings'BOOL_OP;OR;COMPOSITE_TEST;<Unused>;TEST @Value(markeringAvStriper) = malteStriper'GDF.gml#GDF.PedestrianCrossingType.zebraCrossingWithOrWithoutAdditionalAids'FME_NUM_CONDITIONS3___
      SET_TO property{3}.GenericFeatureProperty.memberName = level
      SET_TO property{3}.GenericFeatureProperty.propertyTypeReference.xlink_href = $(Gdf_fcName).gml#$(Gdf_fcName).@Value(fme_feature_type).level
      SET_TO property{3}.GenericFeatureProperty.propertyStructure = listedValue
      SET_TO property{3}.GenericFeatureProperty.valueReference.xlink_href = GDF.gml#GDF.PedestrianCrossingLevel.streetLevelCrossing
    -> AttributeManager_9
AttributeManager_9
    ATTR_TABLE:
      RENAME_SET_VALUE startdato > validFrom
      SET_TO beginLifespanVersion = @Value(validFrom)
      SET_TO typeName = @Value(fme_feature_type)
      SET_TO featureTypeReference.xlink_href = $(Gdf_fcName).gml#$(Gdf_fcName).@Value(fme_feature_type)
    -> DateTimeConverter

Bookmark: Stedfesting
DateTimeConverter
    DATETIME_ATTR = beginLifespanVersion
    OUT_FORMAT = %Y-%m-%dT%H:%M:%S
    PASSTHROUGH = NO
    REPAIR_INPUT = YES
    -> GeometryExtractor
    <REJECTED> -> GeometryExtractor
GeometryExtractor
    ATTR = GeometryLocationReference.encodedGeometry
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = No
    -> ListElementCounter
ListElementCounter
    CNT_ATTR = _element_count
    LIST_NAME = LinearLocationReference.networkReference{}
    -> TestFilter
TestFilter
    DEFAULT_VALUE = <UNFILTERED>
    TEST_LIST = "BOOL_OP,OR,COMPOSITE_TEST,""""""<Unused>"""""",TEST_CLAUSE,TEST @Value(_element_count) = 0",noList
    noList -> Aggregator
    <UNFILTERED> -> AttributeRemover_2
    <UNFILTERED> -> AttributeRemover
Note: Fjerne GeometryLocation
AttributeRemover
    REMOVE_ATTRS = GeometryLocationReference.encodedGeometry
    -> Aggregator
Note: Fjerner LinearLocations
AttributeRemover_2
    LIST_ATTRS = LinearLocationReference.networkReference{} LinearLocationReference.networkReference{}.SimpleLinearReference.applicableDirection LinearLocationReference.networkReference{}.SimpleLinearReference.element.xlink_href LinearLocationReference.networkReference{}.SimpleLinearReference.fromPosition.LR_DistanceExpression.distanceAlong LinearLocationReference.networkReference{}.SimpleLinearReference.fromPosition.LR_DistanceExpression.distanceAlong.uom LinearLocationReference.networkReference{}.SimpleLinearReference.toPosition.LR_DistanceExpression.distanceAlong LinearLocationReference.networkReference{}.SimpleLinearReference.toPosition.LR_DistanceExpression.distanceAlong.uom LinearLocationReference.networkReference{}.SimplePointReference.applicableDirection LinearLocationReference.networkReference{}.SimplePointReference.atPosition.LR_DistanceExpression.distanceAlong LinearLocationReference.networkReference{}.SimplePointReference.atPosition.LR_DistanceExpression.distanceAlong.uom LinearLocationReference.networkReference{}.SimplePointReference.element.xlink_href
    -> Aggregator
Note: Slår sammen og bygger liste
Aggregator
    ACCUM_ATTRS_NAME = Use Attributes From One Feature
    AGGREGATE_TYPE = Homogeneous Collection (If Possible)
    GROUP_BY = gml_id
    LIST_ATTRS_TO_INCLUDE = GeometryLocationReference.encodedGeometry LinearLocationReference.networkReference{}.SimpleLinearReference.applicableDirection LinearLocationReference.networkReference{}.SimpleLinearReference.element.xlink_href LinearLocationReference.networkReference{}.SimpleLinearReference.fromPosition.LR_DistanceExpression.distanceAlong LinearLocationReference.networkReference{}.SimpleLinearReference.fromPosition.LR_DistanceExpression.distanceAlong.uom LinearLocationReference.networkReference{}.SimpleLinearReference.toPosition.LR_DistanceExpression.distanceAlong LinearLocationReference.networkReference{}.SimpleLinearReference.toPosition.LR_DistanceExpression.distanceAlong.uom LinearLocationReference.networkReference{}.SimplePointReference.applicableDirection LinearLocationReference.networkReference{}.SimplePointReference.atPosition.LR_DistanceExpression.distanceAlong LinearLocationReference.networkReference{}.SimplePointReference.atPosition.LR_DistanceExpression.distanceAlong.uom LinearLocationReference.networkReference{}.SimplePointReference.element.xlink_href
    LIST_NAME = locationReference
    MODE = Geometry - Assemble One Level
    ORDERED = No
    SEP = ,
    AGGREGATE -> Feature (writer GML_2)

FME custom transformer NVDB_Leser
Leser og tolker data fra NVDB-API

Parameters:
- NESTE.HREF = @Value(neste.href)   # neste.href

_Input (input)
    -> HTTPCaller_2
Loop (input)
    -> HTTPCaller_2
HTTPCaller_2
    CONNECTION_TIMEOUT_LENGTH = 60
    CUSTOM_HEADERS = Accept;application/vnd.vegvesen.nvdb-v2+xml
    ERROR_ATTR = _error
    FOLLOW_REDIRECTS = Yes
    HTTP_METHOD = GET
    RESPONSE_HEADER_LIST_ATTR = _headers
    SAVE_FILE = Attribute
    STATUS_CODE_ATTR = _http_status_code
    TARGET_ATTR = _url_contents
    TARGET_ATTR_ENCODING = auto-detect
    TARGET_URL = @Value(neste.href)
    TRANSFER_TIMEOUT_LENGTH = 90
    USE_COOKIES = No
    VERIFY_SSL_CERTIFICATES = Yes
    -> XMLFragmenter_2
    -> XMLFragmenter
Note: Kan det defineres at et element SKAL blli en liste? Vil i så fall kunne forenkle koden i NVDBTranslator mye. / Se under cardinality under dokumentasjon i XML Fragmenter
Note: Deler opp i en XML pr vegobjekt
XMLFragmenter
    ATTRIBUTE_XML = _url_contents
    EMBEDDED_EXPRESSIONS = vegobjekt
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = id geometri.wkt
    XML_SOURCE_TYPE = Attribute with XML document
    FRAGMENTS -> NVDBTranslator_2
Note: Oversetter fra NVDB-API-XML
NVDBTranslator_2: PythonCaller
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype epsg kommunenummer startdato LinearLocationReference.networkReference{}.SimpleLinearReference.element.xlink_href LinearLocationReference.networkReference{}.SimplePointReference.element.xlink_href LinearLocationReference.networkReference{}.SimpleLinearReference.fromPosition.LR_DistanceExpression.distanceAlong LinearLocationReference.networkReference{}.SimpleLinearReference.toPosition.LR_DistanceExpression.distanceAlong LinearLocationReference.networkReference{}.SimplePointReference.atPosition.LR_DistanceExpression.distanceAlong LinearLocationReference.networkReference{}.SimpleLinearReference.fromPosition.LR_DistanceExpression.distanceAlong.uom LinearLocationReference.networkReference{}.SimpleLinearReference.toPosition.LR_DistanceExpression.distanceAlong.uom LinearLocationReference.networkReference{}.SimplePointReference.atPosition.LR_DistanceExpression.distanceAlong.uom LinearLocationReference.networkReference{}.SimpleLinearReference.applicableDirection LinearLocationReference.networkReference{}.SimplePointReference.applicableDirection
    PYTHONSOURCE:
      import fme
      import fmeobjects

      def extractNVDB_XML(feature):

          ns='vegvesen.no.nvdb' # FME_MacroValues['namespace']

          # Setter feature type
          ft=str(feature.getAttribute('metadata.type.id'))
          feature.setAttribute('fme_feature_type',ft)
          feature.removeAttribute('metadata.type.id')
          # ID og versjon
          feature.setAttribute('identifikasjon.Identifikasjon.navnerom', ns)
          v=feature.getAttribute('id')
          feature.setAttribute('NVDB_ID', v)
          feature.setAttribute('identifikasjon.Identifikasjon.lokalId', v)
          feature.setAttribute('gml_id', ns + '.' + v)
          feature.removeAttribute('id')
          v=feature.getAttribute('metadata.versjon')
          feature.setAttribute('versjonsID', v)
          v=feature.getAttribute('metadata.startdato')
          feature.setAttribute('startdato', v)
          feature.setAttribute('identifikasjon.Identifikasjon.versjonId', v)
          feature.removeAttribute('metadata.versjon')

          # Kommune
          v=feature.getAttribute('lokasjon.kommuner.kommune')
          feature.setAttribute('kommunenummer', v.zfill(4))
          feature.removeAttribute('lokasjon.kommuner.kommune')

          # Henter ut egenskaper
          i = 0
          while True:
              n = feature.getAttribute('egenskaper.egenskap{%d}.id' % i)
              e = str(feature.getAttribute('egenskaper.egenskap{%d}.enum_id' % i))
              v = feature.getAttribute('egenskaper.egenskap{%d}.verdi' % i)
              if v == None:
                  if i>0:
                      break
                  else:
                      # Kun én egenskap, ikke liste
                      n = feature.getAttribute('egenskaper.egenskap.id')
                      e = str(feature.getAttribute('egenskaper.egenskap.enum_id'))
                      v = feature.getAttribute('egenskaper.egenskap.verdi')
                      feature.removeAttribute('egenskaper.egenskap.datatype')
                      feature.removeAttribute('egenskaper.egenskap.datatype_tekst')
                      feature.removeAttribute('egenskaper.egenskap.enhet.id')
                      feature.removeAttribute('egenskaper.egenskap.enhet.kortnavn')
                      feature.removeAttribute('egenskaper.egenskap.enhet.navn')
                      feature.removeAttribute('egenskaper.egenskap.enum_id')
                      feature.removeAttribute('egenskaper.egenskap.id')
                      feature.removeAttribute('egenskaper.egenskap.navn')
                      feature.removeAttribute('egenskaper.egenskap.verdi')

              if n != None:
                  if e == 'None':
                      # if (n == 'Kommunenummer' and v == 0):
                      feature.setAttribute(n, v)
                  else:
                      # Enumverdi for kodelisteverdier
                      feature.setAttribute(n, e)

              feature.removeAttribute('egenskaper.egenskap{%d}.datatype' % i)
              feature.removeAttribute('egenskaper.egenskap{%d}.datatype_tekst' % i)
              feature.removeAttribute('egenskaper.egenskap{%d}.enhet.id' % i)
              feature.removeAttribute('egenskaper.egenskap{%d}.enhet.kortnavn' % i)
              feature.removeAttribute('egenskaper.egenskap{%d}.enhet.navn' % i)
              feature.removeAttribute('egenskaper.egenskap{%d}.enum_id' % i)
              feature.removeAttribute('egenskaper.egenskap{%d}.id' % i)
              feature.removeAttribute('egenskaper.egenskap{%d}.navn' % i)
              feature.removeAttribute('egenskaper.egenskap{%d}.verdi' % i)
              i += 1


          # Geometri
          v=feature.getAttribute('geometri.egengeometri')
          if v != None:
              feature.setAttribute('egengeometri', v)
          if v == 'true':
              feature.setAttribute('prosesshistorie', 'Geometri: Egengeometri fra NVDB')
          else:
              feature.setAttribute('prosesshistorie', 'Geometri: Generert fra lineære referanser til vegnett i NVDB')
          feature.removeAttribute('geometri.egengeometri')
          v=feature.getAttribute('geometri.srid')
          if v != None:
              feature.setAttribute('epsg', 'EPSG:'+v)
          feature.removeAttribute('geometri.srid')
          v=feature.getAttribute('geometri.wkt')
          if v != None:
              feature.setAttribute('geometri', v)
          feature.removeAttribute('geometri.wkt')

          # Stedfesting i basisnettet
          i = 0
          while True:
              v = str(feature.getAttribute('lokasjon.stedfestinger.stedfesting{%d}.veglenkeid' % i))
              if v == 'None':
                  if i>0:
                      break
                  else:
                      # Kun en stedfesting, hent fra attributt i stedet for fra liste
                      v = str(feature.getAttribute('lokasjon.stedfestinger.stedfesting.posisjon'))
                      if v == 'None':
                          #Ikke verdi for "posisjon", dvs strekningsstedfesting (eller ingen!)
                          v = str(feature.getAttribute('lokasjon.stedfestinger.stedfesting.veglenkeid'))
                          if v != 'None':
                              feature.setAttribute(u'LinearLocationReference.networkReference{%d}.SimpleLinearReference.element.xlink_href' % i, 'Network.gml#' + ns + '.rls.' + v)
                              feature.setAttribute(u'LinearLocationReference.networkReference{%d}.SimpleLinearReference.veglenkeid' % i, v)
                              feature.setAttribute(u'LinearLocationReference.networkReference{%d}.SimpleLinearReference.lenkesekvens.Identifikasjon.navnerom' % i, ns + '.rls')
                              feature.setAttribute(u'LinearLocationReference.networkReference{%d}.SimpleLinearReference.lenkesekvens.Identifikasjon.lokalId' % i, v)
                          v = str(feature.getAttribute('lokasjon.stedfestinger.stedfesting.fra_posisjon'))
                          if v != 'None':
                              feature.setAttribute(u'LinearLocationReference.networkReference{%d}.SimpleLinearReference.fromPosition.LR_DistanceExpression.distanceAlong' % i, v)
                              feature.setAttribute(u'LinearLocationReference.networkReference{%d}.SimpleLinearReference.fromPosition.LR_DistanceExpression.distanceAlong.uom' % i, 'interpolative')
                          v = str(feature.getAttribute('lokasjon.stedfestinger.stedfesting.til_posisjon'))
                          if v != 'None':
                              feature.setAttribute(u'LinearLocationReference.networkReference{%d}.SimpleLinearReference.toPosition.LR_DistanceExpression.distanceAlong' % i, v)
                              feature.setAttribute(u'LinearLocationReference.networkReference{%d}.SimpleLinearReference.toPosition.LR_DistanceExpression.distanceAlong.uom' % i, 'interpolative')

                          v = str(feature.getAttribute('lokasjon.stedfestinger.stedfesting.sideposisjon'))
                          if v != 'None':
                              feature.setAttribute(u'LinearLocationReference.networkReference{%d}.SimpleLinearReference.sideposisjon' % i, v)

                          v = str(feature.getAttribute('lokasjon.stedfestinger.stedfesting.retning'))
                          if v != 'None':
                              if v == 'MED':
                                  feature.setAttribute(u'LinearLocationReference.networkReference{%d}.SimpleLinearReference.applicableDirection' % i, 'inDirection')
                              else:
                                  feature.setAttribute(u'LinearLocationReference.networkReference{%d}.SimpleLinearReference.applicableDirection' % i, 'inOppositeDirection')
                          else:
                              feature.setAttribute(u'LinearLocationReference.networkReference{%d}.SimpleLinearReference.applicableDirection' % i, 'bothDirections')

                          feature.setAttribute(u'LinearLocationReference.networkReference{%d}.SimpleLinearReference.lineærReferanseMetode' % i, 'normalisert')

                      else:
                          # Punktstedfesting
                          v = str(feature.getAttribute('lokasjon.stedfestinger.stedfesting.veglenkeid'))
                          if v != 'None':
                              feature.setAttribute(u'LinearLocationReference.networkReference{%d}.SimplePointReference.element.xlink_href' % i, 'Network.gml#' + ns + '.rls.' + v)
                              feature.setAttribute(u'LinearLocationReference.networkReference{%d}.SimplePointReference.veglenkeid' % i, v)
                          feature.setAttribute(u'LinearLocationReference.networkReference{%d}.SimplePointReference.lenkesekvens.Identifikasjon.navnerom'  % i, ns + '.rls')
                          feature.setAttribute(u'LinearLocationReference.networkReference{%d}.SimplePointReference.lenkesekvens.Identifikasjon.lokalId'  % i, v)

                          v = str(feature.getAttribute('lokasjon.stedfestinger.stedfesting.posisjon'))
                          if v != 'None':
                              feature.setAttribute(u'LinearLocationReference.networkReference{%d}.SimplePointReference.atPosition.LR_DistanceExpression.distanceAlong' % i, v)
                              feature.setAttribute(u'LinearLocationReference.networkReference{%d}.SimplePointReference.atPosition.LR_DistanceExpression.distanceAlong.uom' % i, 'interpolative')
                          v = str(feature.getAttribute(u'lokasjon.stedfestinger.stedfesting.sideposisjon'))
                          if v != 'None':
                              feature.setAttribute(u'LinearLocationReference.networkReference{%d}.SimplePointReference.sideposisjon' % i, v)

                          v = str(feature.getAttribute('lokasjon.stedfestinger.stedfesting.sideposisjon'))
                          if v != 'None':
                              feature.setAttribute(u'LinearLocationReference.networkReference{%d}.SimplePointReference.sideposisjon' % i, v)

                          v = str(feature.getAttribute('lokasjon.stedfestinger.stedfesting.retning'))
                          if v != 'None':
                              if v == 'MED':
                                  feature.setAttribute(u'LinearLocationReference.networkReference{%d}.SimplePointReference.applicableDirection' % i, 'inDirection')
                              else:
                                  feature.setAttribute(u'LinearLocationReference.networkReference{%d}.SimplePointReference.applicableDirection' % i, 'inOppositeDirection')
                          else:
                              feature.setAttribute(u'LinearLocationReference.networkReference{%d}.SimplePointReference.applicableDirection' % i, 'bothDirections')



                          feature.setAttribute(u'LinearLocationReference.networkReference{%d}.SimplePointReference.lineærReferanseMetode' % i, 'normalisert')

                      feature.removeAttribute('lokasjon.stedfestinger.stedfesting.veglenkeid')
                      feature.removeAttribute('lokasjon.stedfestinger.stedfesting.fra_posisjon')
                      feature.removeAttribute('lokasjon.stedfestinger.stedfesting.til_posisjon')
                      feature.removeAttribute('lokasjon.stedfestinger.stedfesting.posisjon')
                      feature.removeAttribute('lokasjon.stedfestinger.stedfesting.sideposisjon')
                      # feature.removeAttribute('lokasjon.stedfestinger.stedfesting.retning')
                      feature.removeAttribute('lokasjon.stedfestinger.stedfesting.kortform')
              else:
                  # Bygg LineærPosisjon-liste fra stedfestingsliste
                  v = str(feature.getAttribute('lokasjon.stedfestinger.stedfesting{%d}.posisjon' % i))
                  if v == 'None':
                      #Ikke verdi for "posisjon", dvs strekningsstedfesting
                      v = str(feature.getAttribute('lokasjon.stedfestinger.stedfesting{%d}.veglenkeid' % i))
                      if v != 'None':
                          feature.setAttribute(u'LinearLocationReference.networkReference{%d}.SimpleLinearReference.element.xlink_href' % i, 'Network.gml#' + ns + '.rls.' + v)
                          feature.setAttribute(u'LinearLocationReference.networkReference{%d}.SimpleLinearReference.veglenkeid' % i, v)
                          feature.setAttribute(u'LinearLocationReference.networkReference{%d}.SimpleLinearReference.lenkesekvens.Identifikasjon.navnerom'  % i, ns + '.rls')
                          feature.setAttribute(u'LinearLocationReference.networkReference{%d}.SimpleLinearReference.lenkesekvens.Identifikasjon.lokalId'  % i, v)

                      v = str(feature.getAttribute('lokasjon.stedfestinger.stedfesting{%d}.fra_posisjon' % i))
                      if v != 'None':
                          feature.setAttribute(u'LinearLocationReference.networkReference{%d}.SimpleLinearReference.fromPosition.LR_DistanceExpression.distanceAlong' % i, v)
                          feature.setAttribute(u'LinearLocationReference.networkReference{%d}.SimpleLinearReference.fromPosition.LR_DistanceExpression.distanceAlong.uom' % i, 'interpolative')
                      v = str(feature.getAttribute('lokasjon.stedfestinger.stedfesting{%d}.til_posisjon' % i))
                      if v != 'None':
                          feature.setAttribute(u'LinearLocationReference.networkReference{%d}.SimpleLinearReference.toPosition.LR_DistanceExpression.distanceAlong' % i, v)
                          feature.setAttribute(u'LinearLocationReference.networkReference{%d}.SimpleLinearReference.toPosition.LR_DistanceExpression.distanceAlong.uom' % i, 'interpolative')
                      v = str(feature.getAttribute('lokasjon.stedfestinger.stedfesting{%d}.sideposisjon' % i))
                      if v != 'None':
                          feature.setAttribute(u'LinearLocationReference.networkReference{%d}.SimpleLinearReference.sideposisjon' % i, v)

                      v = str(feature.getAttribute('lokasjon.stedfestinger.stedfesting{%d}.retning' % i))
                      if v != 'None':
                          if v == 'MED':
                              feature.setAttribute(u'LinearLocationReference.networkReference{%d}.SimpleLinearReference.applicableDirection' % i, 'inDirection')
                          else:
                              feature.setAttribute(u'LinearLocationReference.networkReference{%d}.SimpleLinearReference.applicableDirection' % i, 'inOppositeDirection')
                      else:
                          feature.setAttribute(u'LinearLocationReference.networkReference{%d}.SimpleLinearReference.applicableDirection' % i, 'bothDirections')

                      feature.setAttribute(u'LinearLocationReference.networkReference{%d}.SimpleLinearReference.lineærReferanseMetode' % i, 'normalisert')

                  else:
                      # Punktstedfesting
                      v = str(feature.getAttribute('lokasjon.stedfestinger.stedfesting{%d}.veglenkeid' % i))
                      if v != 'None':
                          feature.setAttribute(u'LinearLocationReference.networkReference{%d}.SimplePointReference.element.xlink_href' % i, 'Network.gml#' + ns + '.rls.' + v)
                          feature.setAttribute(u'LinearLocationReference.networkReference{%d}.SimplePointReference.veglenkeid' % i, v)
                          feature.setAttribute(u'LinearLocationReference.networkReference{%d}.SimplePointReference.lenkesekvens.Identifikasjon.navnerom'  % i, ns + '.rls')
                          feature.setAttribute(u'LinearLocationReference.networkReference{%d}.SimplePointReference.lenkesekvens.Identifikasjon.lokalId'  % i, v)

                      v = str(feature.getAttribute('lokasjon.stedfestinger.stedfesting{%d}.posisjon' % i))
                      if v != 'None':
                          feature.setAttribute(u'LinearLocationReference.networkReference{%d}.SimplePointReference.atPosition.LR_DistanceExpression.distanceAlong' % i, v)
                          feature.setAttribute(u'LinearLocationReference.networkReference{%d}.SimplePointReference.atPosition.LR_DistanceExpression.distanceAlong.uom' % i, 'interpolative')
                      v = str(feature.getAttribute('lokasjon.stedfestinger.stedfesting{%d}.sideposisjon' % i))
                      if v != 'None':
                          feature.setAttribute(u'LinearLocationReference.networkReference{%d}.SimplePointReference.sideposisjon' % i, v)

                      v = str(feature.getAttribute('lokasjon.stedfestinger.stedfesting{%d}.retning' % i))
                      if v != 'None':
                          if v == 'MED':
                              feature.setAttribute(u'LinearLocationReference.networkReference{%d}.SimpleLinearReference.applicableDirection' % i, 'inDirection')
                          else:
                              feature.setAttribute(u'LinearLocationReference.networkReference{%d}.SimpleLinearReference.applicableDirection' % i, 'inOppositeDirection')
                      else:
                          feature.setAttribute(u'LinearLocationReference.networkReference{%d}.SimpleLinearReference.applicableDirection' % i, 'bothDirections')

                      feature.setAttribute(u'LinearLocationReference.networkReference{%d}.SimplePointReference.lineærReferanseMetode' % i, 'normalisert')

                  feature.removeAttribute('lokasjon.stedfestinger.stedfesting{%d}.veglenkeid' % i)
                  feature.removeAttribute('lokasjon.stedfestinger.stedfesting{%d}.fra_posisjon' % i)
                  feature.removeAttribute('lokasjon.stedfestinger.stedfesting{%d}.til_posisjon' % i)
                  feature.removeAttribute('lokasjon.stedfestinger.stedfesting{%d}.posisjon' % i)
                  feature.removeAttribute('lokasjon.stedfestinger.stedfesting{%d}.sideposisjon' % i)
                  feature.removeAttribute('lokasjon.stedfestinger.stedfesting{%d}.retning' % i)
                  feature.removeAttribute('lokasjon.stedfestinger.stedfesting{%d}.kortform' % i)
              i += 1

          # Vegreferanse
          i = 0
          while True:
              v = str(feature.getAttribute('lokasjon.vegreferanser.vegreferanse{%d}.kategori' % i))
              if v == 'None':
                  if i>0:
                      break
                  else:
                      # Kun en stedfesting, hent fra attributt i stedet for fra liste
                      v = str(feature.getAttribute('lokasjon.vegreferanser.vegreferanse.kategori'))
                      if v != 'None':
                          feature.setAttribute('vegreferanse{%d}.Vegreferanse.vegkategori' % i, v)
                          feature.removeAttribute('lokasjon.vegreferanser.vegreferanse.kategori')

                      v = str(feature.getAttribute('lokasjon.vegreferanser.vegreferanse.nummer'))
                      if v != 'None':
                          feature.setAttribute('vegreferanse{%d}.Vegreferanse.vegnummer' % i, v)
                          feature.removeAttribute('lokasjon.vegreferanser.vegreferanse.nummer')

                      v = str(feature.getAttribute('lokasjon.vegreferanser.vegreferanse.status'))
                      if v != 'None':
                          feature.setAttribute('vegreferanse{%d}.Vegreferanse.vegstatus' % i, v)
                          feature.removeAttribute('lokasjon.vegreferanser.vegreferanse.status')

                      v = str(feature.getAttribute('lokasjon.vegreferanser.vegreferanse.hp'))
                      if v != 'None':
                          feature.setAttribute('vegreferanse{%d}.Vegreferanse.hovedparsell' % i, v)
                          feature.removeAttribute('lokasjon.vegreferanser.vegreferanse.hp')

                      v = str(feature.getAttribute('lokasjon.vegreferanser.vegreferanse.fra_meter'))
                      if v != 'None':
                          feature.setAttribute('vegreferanse{%d}.Vegreferanse.veglenkeMeterFra' % i, v)
                          feature.removeAttribute('lokasjon.vegreferanser.vegreferanse.fra_meter')

                      v = str(feature.getAttribute('lokasjon.vegreferanser.vegreferanse.til_meter'))
                      if v != 'None':
                          feature.setAttribute('vegreferanse{%d}.Vegreferanse.veglenkeMeterTil' % i, v)
                          feature.removeAttribute('lokasjon.vegreferanser.vegreferanse.til_meter')

                      v = str(feature.getAttribute('lokasjon.vegreferanser.vegreferanse.meter'))
                      if v != 'None':
                          feature.setAttribute('vegreferanse{%d}.Vegreferanse.veglenkeMeterFra' % i, v)
                          feature.setAttribute('vegreferanse{%d}.Vegreferanse.veglenkeMeterTil' % i, v)
                          feature.removeAttribute('lokasjon.vegreferanser.vegreferanse.meter')

                      v = str(feature.getAttribute('lokasjon.vegreferanser.vegreferanse.fylke'))
                      if v != 'None':
                          feature.setAttribute('vegreferanse{%d}.Vegreferanse.fylke' % i, v)
                          feature.removeAttribute('lokasjon.vegreferanser.vegreferanse.fylke')
                      v = str(feature.getAttribute('lokasjon.vegreferanser.vegreferanse.kommune'))
                      if v != 'None':
                          feature.setAttribute('vegreferanse{%d}.Vegreferanse.kommune' % i, v)
                          feature.removeAttribute('lokasjon.vegreferanser.vegreferanse.kommune')

                      feature.removeAttribute('lokasjon.vegreferanser.vegreferanse.kortform')
              else:
                  # Bygg vegreferanse-liste fra stedfestingsliste
                  v = str(feature.getAttribute('lokasjon.vegreferanser.vegreferanse{%d}.fylke'))
                  if v != 'None':
                      feature.setAttribute('vegreferanse{%d}.Vegreferanse.fylke' % i, v)
                      feature.removeAttribute('lokasjon.vegreferanser.vegreferanse{%d}.fylke')
                  else:
                      # Henter fylke fra 'fylker'-taggen
                      v = str(feature.getAttribute('lokasjon.fylker.fylke'))
                      if v != 'None':
                          feature.setAttribute('vegreferanse{%d}.Vegreferanse.fylke' % i, v)
                          feature.removeAttribute('lokasjon.vegreferanser.vegreferanse{%d}.fylke')

                  v = str(feature.getAttribute('lokasjon.vegreferanser.vegreferanse{%d}.kommune'))
                  if v != 'None':
                      feature.setAttribute('vegreferanse{%d}.Vegreferanse.kommune' % i, v)
                      feature.removeAttribute('lokasjon.vegreferanser.vegreferanse{%d}.kommune')
                  else:
                      v = str(feature.getAttribute('lokasjon.vegreferanser.vegreferanse{%d}.kategori' % i))
                      if (v=='K' or v=='P' or v=='S'):
                          # Henter kommune fra 'kommuner'-taggen
                          v = str(feature.getAttribute('lokasjon.kommuner.kommune'))
                          if v != 'None':
                              feature.setAttribute('vegreferanse{%d}.Vegreferanse.kommune' % i, v)
                      else:
                          feature.setAttribute('vegreferanse{%d}.Vegreferanse.kommune' % i, '0')
                      feature.removeAttribute('lokasjon.vegreferanser.vegreferanse{%d}.kommune')

                  v = str(feature.getAttribute('lokasjon.vegreferanser.vegreferanse{%d}.kategori' % i))
                  if v != 'None':
                      feature.setAttribute('vegreferanse{%d}.Vegreferanse.vegkategori' % i, v)
                      feature.removeAttribute('lokasjon.vegreferanser.vegreferanse{%d}.kategori' % i)

                  v = str(feature.getAttribute('lokasjon.vegreferanser.vegreferanse{%d}.nummer' % i))
                  if v != 'None':
                      feature.setAttribute('vegreferanse{%d}.Vegreferanse.vegnummer' % i, v)
                      feature.removeAttribute('lokasjon.vegreferanser.vegreferanse{%d}.nummer' % i)

                  v = str(feature.getAttribute('lokasjon.vegreferanser.vegreferanse{%d}.status' % i))
                  if v != 'None':
                      feature.setAttribute('vegreferanse{%d}.Vegreferanse.vegstatus' % i, v)
                      feature.removeAttribute('lokasjon.vegreferanser.vegreferanse{%d}.status' % i)

                  v = str(feature.getAttribute('lokasjon.vegreferanser.vegreferanse{%d}.hp' % i))
                  if v != 'None':
                      feature.setAttribute('vegreferanse{%d}.Vegreferanse.hovedparsell' % i, v)
                      feature.removeAttribute('lokasjon.vegreferanser.vegreferanse{%d}.hp' % i)

                  v = str(feature.getAttribute('lokasjon.vegreferanser.vegreferanse{%d}.fra_meter' % i))
                  if v != 'None':
                      feature.setAttribute('vegreferanse{%d}.Vegreferanse.veglenkeMeterFra' % i, v)
                      feature.removeAttribute('lokasjon.vegreferanser.vegreferanse{%d}.fra_meter' % i)

                  v = str(feature.getAttribute('lokasjon.vegreferanser.vegreferanse{%d}.til_meter' % i))
                  if v != 'None':
                      feature.setAttribute('vegreferanse{%d}.Vegreferanse.veglenkeMeterTil' % i, v)
                      feature.removeAttribute('lokasjon.vegreferanser.vegreferanse{%d}.til_meter' % i)

                  v = str(feature.getAttribute('lokasjon.vegreferanser.vegreferanse{%d}.meter'))
                  if v != 'None':
                      feature.setAttribute('vegreferanse{%d}.Vegreferanse.veglenkeMeterFra' % i, v)
                      feature.setAttribute('vegreferanse{%d}.Vegreferanse.veglenkeMeterTil' % i, v)
                      feature.removeAttribute('lokasjon.vegreferanser.vegreferanse{%d}.meter')

                  feature.removeAttribute('lokasjon.vegreferanser.vegreferanse{%d}.kortform' % i)
              i += 1


          # Assosiasjoner: Barn
          t = 0
          i = 0
          while True:
              p=str(feature.getAttribute('relasjoner.barn.barn{%d}.type.id' % i))
              lst='false'
              if p == 'None':
                  if i>0:
                      break
                  else:
                      # Kun ett barn, hent assosiert typeid fra attributt i stedet for fra liste
                      typeid = str(feature.getAttribute('relasjoner.barn.barn.type.id'))
                      if typeid != 'None':
                          feature.removeAttribute('relasjoner.barn.barn.type.id')
                          feature.removeAttribute('relasjoner.barn.barn.type.navn')
                      else:
                          # Ingen barn
                          break
              else:
                  #Hent assosiert typeid fra liste
                  lst='true'
                  typeid=str(feature.getAttribute('relasjoner.barn.barn{%d}.type.id' % i))
                  feature.removeAttribute('relasjoner.barn.barn{%d}.type.id' % i)
                  feature.removeAttribute('relasjoner.barn.barn{%d}.type.navn' % i)

              # Løkke for assosierte vegobjekter
              votid='None'
              if lst=='true':
                  #Assosiasjonstyper i liste
                  p = feature.getAttribute('relasjoner.barn.barn{%d}.vegobjekter.id{}' % i)
                  if p == None:
                      # Ikke liste i liste
                      votid=str(feature.getAttribute('relasjoner.barn.barn{%d}.vegobjekter.id' % i))
                      feature.removeAttribute('relasjoner.barn.barn{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'barn')
                      #print votid,t
                      t+=1
                  else:
                      # Løkke for liste med vegobjekt-ider
                      j = 0
                      while True:
                          votid=str(feature.getAttribute('relasjoner.barn.barn{%d}.vegobjekter.id{%d}' % (i,j)))
                          if votid == 'None':
                              break
                          feature.removeAttribute('relasjoner.barn.barn{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              else:
                  # Assosiasjonstype i attributter
                  p = feature.getAttribute('relasjoner.barn.barn.vegobjekter.id{}')
                  if p == None:
                      # Kun ett assosiert objekt
                      votid=str(feature.getAttribute('relasjoner.barn.barn.vegobjekter.id'))
                      feature.removeAttribute('relasjoner.barn.barn.vegobjekter.id')
                      feature.setAttribute('assosiasjoner{%d}.typeId' % t, typeid)
                      feature.setAttribute('assosiasjoner{%d}.vegobjektId' % t, votid)
                      feature.setAttribute('assosiasjoner{%d}.relasjonstype' % t, 'barn')
                      t+=1
                      # print votid,t
                  else:
                      # Løkke for liste med vegobjekt-ider
                      j = 0
                      while True:
                          votid=str(feature.getAttribute('relasjoner.barn.barn.vegobjekter.id{%d}' % j))
                          if votid == 'None':
                              break
                          feature.removeAttribute('relasjoner.barn.barn.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              i += 1

          # Assosiasjoner: foreldre
          # Må telle videre på samme variabel for ny liste (t), ikke starte på nytt!
          i = 0
          while True:
              p=str(feature.getAttribute('relasjoner.foreldre.forelder{%d}.type.id' % i))
              lst='false'
              if p == 'None':
                  if i>0:
                      break
                  else:
                      # Kun en forelder, hent assosiert typeid fra attributt i stedet for fra liste
                      typeid = str(feature.getAttribute('relasjoner.foreldre.forelder.type.id'))
                      if typeid != 'None':
                          feature.removeAttribute('relasjoner.foreldre.forelder.type.id')
                          feature.removeAttribute('relasjoner.foreldre.forelder.type.navn')
                      else:
                          # Ingen foreldre
                          break
              else:
                  #Hent assosiert typeid fra liste
                  lst='true'
                  typeid=str(feature.getAttribute('relasjoner.foreldre.forelder{%d}.type.id' % i))
                  feature.removeAttribute('relasjoner.foreldre.forelder{%d}.type.id' % i)
                  feature.removeAttribute('relasjoner.foreldre.forelder{%d}.type.navn' % i)

              # Løkke for assosierte vegobjekter
              votid='None'
              if lst=='true':
                  #Assosiasjonstyper i liste
                  p = feature.getAttribute('relasjoner.foreldre.forelder{%d}.vegobjekter.id{}' % i)
                  if p == None:
                      # Ikke liste i liste
                      votid=str(feature.getAttribute('relasjoner.foreldre.forelder{%d}.vegobjekter.id' % i))
                      feature.removeAttribute('relasjoner.foreldre.forelder{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder{%d}.vegobjekter.id{%d}' % (i,j)))
                          if votid == 'None':
                              break
                          feature.removeAttribute('relasjoner.foreldre.forelder{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              else:
                  # Assosiasjonstype i attributter
                  p = feature.getAttribute('relasjoner.foreldre.forelder.vegobjekter.id{}')
                  if p == None:
                      # Kun ett assosiert objekt
                      votid=str(feature.getAttribute('relasjoner.foreldre.forelder.vegobjekter.id'))
                      feature.removeAttribute('relasjoner.foreldre.forelder.vegobjekter.id')
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder.vegobjekter.id{%d}' % j))
                          if votid == 'None':
                              break
                          feature.removeAttribute('relasjoner.foreldre.forelder.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              i += 1
    PYTHONSYMBOL = extractNVDB_XML
    -> GeometryReplacer
Note: Geometri
GeometryReplacer
    KIND_LONG = OGC Well Known Text
    OGC_WKT_PRECISION_DISPLAY = 64-bit
    REMOVE_ATTRIBUTE = Yes
    SOURCE = @Value(geometri)
    -> CoordinateSystemSetter
    -> CoordinateSystemSetter_2
    -> 3DForcer
3DForcer
    KEEPZVAL = Yes
    ZVALATTR = NaN
    -> CoordinateSystemSetter_3
CoordinateSystemSetter_3
    COORDSYS = EPSG:6173
    -> Deaggregator
CoordinateSystemSetter [off]
    COORDSYS = @Value(epsg)
    -> Deaggregator
CoordinateSystemSetter_2 [off]
    COORDSYS = EPSG:25833
    -> Deaggregator
XMLFragmenter_2
    ATTRIBUTE_XML = _url_contents
    EMBEDDED_EXPRESSIONS = side/metadata
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = returnert neste.href
    XML_SOURCE_TYPE = Attribute with XML document
    FRAGMENTS -> TestFilter
TestFilter
    DEFAULT_VALUE = <UNFILTERED>
    TEST_LIST = BOOL_OP,OR,COMPOSITE_TEST,<Unused>,TEST_CLAUSE,"TEST @Value(returnert) != 0",Flere
    Flere -> Loop (output)
Loop (output)

Bookmark: Splitter multigeometrier
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> NullAttributeMapper
NullAttributeMapper
    ATTRCHOICE = Selected Attributes
    ATTRLIST = _part_number
    NEW_VALUE = 0
    NULL_TREATMENT = New Value
    SOURCE_ATTR_VAL = Null Empty "Missing (Selected Attributes Only)"
    -> StringConcatenator
StringConcatenator
    ACTION = Create New Attribute
    PARM_LINE = @Value(gml_id)_@Value(_part_number)
    VAL_ATTR = gml_id
    -> Output (output)
Output (output)

FME custom transformer NVDB_Vegnettleser
Leser og tolker data fra NVDB-API

Parameters:
- NESTE.HREF = @Value(neste.href)   # neste.href
- OMR = @Value(omr)   # omr
- OMRNVN = @Value(omrNvn)   # omrNvn
- namespace = vegvesen.no.nvdb   # Namespace
- nettverk:   # Python Script
      ns = FME_MacroValues['namespace'] + '.nw.' + FME_MacroValues['OMR'] + '_' + FME_MacroValues['OMRNVN']
      return ns

_Input (input)
    -> HTTPCaller_2
Loop (input)
    -> HTTPCaller_2
HTTPCaller_2
    CONNECTION_TIMEOUT_LENGTH = 60
    CUSTOM_HEADERS = Accept;application/vnd.vegvesen.nvdb-v2+xml
    ERROR_ATTR = _error
    FOLLOW_REDIRECTS = Yes
    HTTP_METHOD = GET
    RESPONSE_HEADER_LIST_ATTR = _headers
    SAVE_FILE = Attribute
    STATUS_CODE_ATTR = _http_status_code
    TARGET_ATTR = _url_contents
    TARGET_ATTR_ENCODING = auto-detect
    TARGET_URL = @Value(neste.href)
    TRANSFER_TIMEOUT_LENGTH = 90
    USE_COOKIES = No
    VERIFY_SSL_CERTIFICATES = Yes
    -> XMLFragmenter_2
    -> XMLFragmenter
Note: Deler opp i en XML pr vegobjekt
XMLFragmenter
    ATTRIBUTE_XML = _url_contents
    EMBEDDED_EXPRESSIONS = lenke
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = id geometri.wkt startnode sluttnode veglenkeid
    REJECT_FEATURES_WITH_NO_FRAGMENTS = YES
    XML_SOURCE_TYPE = Attribute with XML document
    FRAGMENTS -> StringReplacer
Note: Bytter "-" med "_" i nodeid
StringReplacer
    CASE = NO
    FIND_TEXT = -
    NO_MATCH = _FME_NO_OP_
    REGEXP = NO
    REPLACE_TEXT = _
    SRC_ATTRS = sluttnode,startnode
    -> NVDBTranslator
Note: Oversetter fra NVDB-API-XML
NVDBTranslator: PythonCaller
    NEW_ATTRIBUTES = geometri fme_feature_type identifikasjon.Identifikasjon.lokalId identifikasjon.Identifikasjon.versjonId identifikasjon.Identifikasjon.navnerom gml_id epsg detaljnivå lenkesekvens.Lenkesekvensreferanse.startposisjon lenkesekvens.Lenkesekvensreferanse.sluttposisjon startnodeId sluttnodeId temakode veglenkeid vegreferanse.Vegreferanse.kommunenummer konnekteringslenke medium datafangstdato typeVeg kommunenummer lenkesekvens.Lenkesekvensreferanse.identifikasjon.Identifikasjon.lokalId foreldrelenkeid vegreferanse.Vegreferanse.vegkategori vegreferanse.Vegreferanse.vegnummer vegreferanse.Vegreferanse.vegstatus vegreferanse.Vegreferanse.hovedparsell vegreferanse.Vegreferanse.veglenkeMeterFra vegreferanse.Vegreferanse.veglenkeMeterTil vegreferanse.Vegreferanse.referanseretning startdato
    PYTHONSOURCE:
      #!/usr/bin/env python
      # -*- coding: utf-8 -*-
      import fme
      import fmeobjects

      def extractNVDB_XML(feature):

          #Namespace
          ns= 'vegvesen.no.nvdb'

          # Setter feature type
          ft='Veglenke'
          feature.setAttribute('fme_feature_type',ft)
          # ID og versjon.  Namespace ...rls for veglenkesekvenser (id på lenkene er lenkesekvensen sin id pluss et løpenummer)
          feature.setAttribute('identifikasjon.Identifikasjon.navnerom', ns + '.rls')
          feature.setAttribute('lenkesekvens.Lenkesekvensreferanse.identifikasjon.Identifikasjon.navnerom', ns + '.rls')
          v=feature.getAttribute('veglenkeid')
          # feature.setAttribute('NVDB_ID', v)
          feature.setAttribute('identifikasjon.Identifikasjon.lokalId', v)
          feature.setAttribute('lenkesekvens.Lenkesekvensreferanse.identifikasjon.Identifikasjon.lokalId', v)
          feature.setAttribute('gml_id', ns + '.rls.' + v)
          v=feature.getAttribute('metadata.startdato')
          feature.setAttribute('startdato', v)
          # feature.removeAttribute('veglenkeid')

          # Kommune
          v=feature.getAttribute('kommune')
          feature.setAttribute('kommunenummer', v.zfill(4))
          feature.removeAttribute('kommune')

          #Lineære posisjoner i lenkesekvensen
          feature.setAttribute('standardLRM', 'normalisert')
          # startposisjon og sluttposisjon må tolkes fra evt eksponentielle tall
          v=feature.getAttribute('startposisjon')
          feature.setAttribute('lenkesekvens.Lenkesekvensreferanse.startposisjon', float(v))
          v=feature.getAttribute('sluttposisjon')
          feature.setAttribute('lenkesekvens.Lenkesekvensreferanse.sluttposisjon', float(v))

          v=feature.getAttribute('felt')
          if v != None:
              feature.setAttribute('feltoversikt',v)

          #Topologi
          #detaljnivå
          #    <topologinivå>1</topologinivå>
          #    <topologinivå_tekst>Kjørebane</topologinivå_tekst>
          v=feature.getAttribute(u'topologinivå')
          if v != None:
              #print v
              if v == '0':
                  feature.setAttribute(u'detaljnivå', u'vegtrase')
              if v == '1':
                  feature.setAttribute(u'detaljnivå', u'kjørebane')
              if v == '2':
                  feature.setAttribute(u'detaljnivå', u'kjørefelt')
              feature.removeAttribute(u'topologinivå_tekst')
             #feature.removeAttribute('topologinivå')

          #noder
          #    <startnode>2373197-1</startnode>
          v=str(feature.getAttribute('startnode'))
          feature.removeAttribute('startnode')
          if v != 'None':
              feature.setAttribute('startNode.xlink_href', '#' + ns + '.rn.' + v)
              feature.setAttribute('startnodeId', v)
          #    <sluttnode>1087601-2</sluttnode>
          v=str(feature.getAttribute('sluttnode'))
          feature.removeAttribute('sluttnode')
          if v != 'None':
              feature.setAttribute('endNode.xlink_href', '#' + ns + '.rn.' + v)
              feature.setAttribute('sluttnodeId', v)


          #Kvalitet
          #            <metode>60</metode>
          v=str(feature.getAttribute(u'geometri.kvalitet.metode'))
          if v != 'None' and v != '-1':
              feature.setAttribute(u'kvalitet.Posisjonskvalitet.målemetode', v)
          feature.removeAttribute(u'geometri.kvalitet.metode')
          #            <nøyaktighet>200</nøyaktighet>
          v=str(feature.getAttribute(u'geometri.kvalitet.nøyaktighet'))
          if v != 'None' and v != '-1':
              feature.setAttribute(u'kvalitet.Posisjonskvalitet.nøyaktighet', v)
          feature.removeAttribute(u'geometri.kvalitet.nøyaktighet')
          #            <høydenøyaktighet>-1</høydenøyaktighet>
          v=str(feature.getAttribute('geometri.kvalitet.høydenøyaktighet'))
          if v != 'None' and v != '-1':
              feature.setAttribute(u'kvalitet.Posisjonskvalitet.nøyaktighetHøyde', v)
          feature.removeAttribute(u'geometri.kvalitet.høydenøyaktighet')
          #            <toleranse>-1</toleranse>
          v=str(feature.getAttribute(u'geometri.kvalitet.toleranse'))
          if v != 'None' and v != '-1':
              feature.setAttribute(u'kvalitet.Posisjonskvalitet.maksimaltAvvik', v)
          feature.removeAttribute(u'geometri.kvalitet.toleranse')
          #            <synlighet>99</synlighet>
          v=str(feature.getAttribute(u'geometri.kvalitet.synlighet'))
          if v == '0' or v == '1' or v == '2' or v == '3' :
              feature.setAttribute(u'kvalitet.Posisjonskvalitet.synbarhet', v)
          feature.removeAttribute(u'geometri.kvalitet.synlighet')
          #            <datafangstdato>2002-12-07</datafangstdato>
          v=str(feature.getAttribute(u'geometri.kvalitet.datafangstdato'))
          if v != 'None' and v != '-1':
              feature.setAttribute(u'datafangstdato', v)
          feature.removeAttribute(u'geometri.kvalitet.datafangstdato')

          # Geometri
          v=feature.getAttribute('geometri.srid')
          if v != None:
              feature.setAttribute('epsg', 'EPSG:'+v)
          feature.removeAttribute('geometri.srid')
          v=feature.getAttribute('geometri.wkt')
          if v != None:
              feature.setAttribute('geometri', v)
          feature.removeAttribute('geometri.wkt')

          # Vegreferanse
          # <vegreferanse>
          #    <fylke>5</fylke>
          v=str(feature.getAttribute('vegreferanse.fylke'))
          if v != 'None' and v != '0':
              feature.setAttribute('vegreferanse.Vegreferanse.fylkesnummer', v.zfill(2))
          feature.removeAttribute('vegreferanse.fylke')
          #    <kommune>520</kommune>
          v=str(feature.getAttribute('vegreferanse.kommune'))
          if v != 'None' and v != '0':
              feature.setAttribute('vegreferanse.Vegreferanse.kommunenummer', v.zfill(4))
          feature.removeAttribute('vegreferanse.kommune')
          #    <kategori>K</kategori>
          v=str(feature.getAttribute('vegreferanse.kategori'))
          if v != 'None':
              feature.setAttribute('vegreferanse.Vegreferanse.vegkategori', v)
          feature.removeAttribute('vegreferanse.kategori')
          #    <status>V</status>
          v=str(feature.getAttribute('vegreferanse.status'))
          if v != 'None':
              feature.setAttribute('vegreferanse.Vegreferanse.vegstatus', v)
          feature.removeAttribute('vegreferanse.status')
          #    <nummer>1161</nummer>
          v=str(feature.getAttribute('vegreferanse.nummer'))
          if v != 'None':
              feature.setAttribute('vegreferanse.Vegreferanse.vegnummer', v)
          feature.removeAttribute('vegreferanse.nummer')
          #    <hp>1</hp>
          v=str(feature.getAttribute('vegreferanse.hp'))
          if v != 'None':
              feature.setAttribute('vegreferanse.Vegreferanse.hovedparsell', v)
          feature.removeAttribute('vegreferanse.hp')
          #    <fra_meter>57</fra_meter>
          f=str(feature.getAttribute('vegreferanse.fra_meter'))
          if f != 'None':
              feature.setAttribute('vegreferanse.Vegreferanse.veglenkeMeterFra', f)
          feature.removeAttribute('vegreferanse.fra_meter')
          #    <til_meter>96</til_meter>
          t=str(feature.getAttribute('vegreferanse.til_meter'))
          if t != 'None':
              feature.setAttribute('vegreferanse.Vegreferanse.veglenkeMeterTil', t)
          feature.removeAttribute('vegreferanse.til_meter')
          #    <kortform>0520 Kv1161 hp1 m57-96</kortform>
          if f!='None' and t!='None':
              if int(f) <= int(t):
                  feature.setAttribute('vegreferanse.Vegreferanse.referanseretning', 'med')
              else:
                  feature.setAttribute('vegreferanse.Vegreferanse.referanseretning', 'mot')
          # </vegreferanse>
    PYTHONSYMBOL = extractNVDB_XML
    -> ListBuilder
ListBuilder
    GRP_BY = identifikasjon.Identifikasjon.lokalId identifikasjon.Identifikasjon.navnerom gml_id identifikasjon.Identifikasjon.versjonId
    LIST_NAME = _linkList
    -> ListSorter
ListSorter
    ORDER = Ascending
    SRC_LIST = _linkList{}.lenkesekvens.Lenkesekvensreferanse.sluttposisjon
    TYPE = Numeric
    -> AttributeCreator
AttributeCreator
    ATTR_TABLE = SET_TO nettverk{0}.xlink_href = #$(nettverk)
    -> Veglenkereferanser
Note: Lager id for Veglenker + referanser fra Veglenkesekvens til Veglenke
Veglenkereferanser: PythonCaller
    NEW_ATTRIBUTES = link{].DirectedLink.direction
    PYTHONSOURCE:
      import fme
      import fmeobjects

      def setLinkID(feature):

          # Namespace ..rl for veglenker
          ns= 'vegvesen.no.nvdb.rl'

          ft='Veglenkesekvens'
          feature.setAttribute('fme_feature_type',ft)

          i = 0
          while True:
              v = feature.getAttribute('_linkList{%d}.identifikasjon.Identifikasjon.lokalId' % i)
              if v == None:
                  break
              localId = str(v) + "_" + str(i)
              feature.setAttribute('_linkList{%d}.identifikasjon.Identifikasjon.lokalId' % i, localId)
              feature.setAttribute('_linkList{%d}.identifikasjon.Identifikasjon.navnerom' % i, ns)
              gml_id = ns + "." + localId
              feature.setAttribute('_linkList{%d}.gml_id' % i, gml_id)

              f=feature.getAttribute('_linkList{%d}.startposisjon' % i)
              t=feature.getAttribute('_linkList{%d}.sluttposisjon' % i)
              if f < t:
                  feature.setAttribute('link{%d}.DirectedLink.direction' % i, '+')
              else:
                  feature.setAttribute('link{%d}.DirectedLink.direction' % i, '-')
              feature.setAttribute('link{%d}.DirectedLink.link.xlink_href' % i, '#' + gml_id)
              i += 1
    PYTHONSYMBOL = setLinkID
    -> Veglenkesekvens (output)
    -> ListExploder
Veglenkesekvens (output)
ListExploder
    ATTR_ACCUM_MODE = Merge Incoming List
    ATTR_CONFLICT_RES = Use Incoming List
    INDEX_ATTR = _element_index
    LIST_ATTR = _linkList{}
    ELEMENTS -> GeometryReplacer
Note: Geometri
GeometryReplacer
    KIND_LONG = OGC Well Known Text
    OGC_WKT_PRECISION_DISPLAY = 64-bit
    REMOVE_ATTRIBUTE = Yes
    SOURCE = @Value(geometri)
    -> 3DForcer
3DForcer
    KEEPZVAL = Yes
    ZVALATTR = NaN
    -> CoordinateSystemSetter
CoordinateSystemSetter
    COORDSYS = EPSG:6173
    -> GeometryPropertySetter_4
    -> AttributeManager_2
    -> AttributeManager_3
Note: Definerer geometriegenskap
GeometryPropertySetter_4
    GEOM_NAME_FIELD = senterlinje
    OVERWRITE_CHOICE = Yes
    SETTYPE_PARAM = Geometry Name
    SET -> DateFormatter
DateFormatter
    DATE_ATTR = datafangstdato
    FMT = ISO Date (%Y-%m-%d)
    INVALID_DATE_VALUE = 0001-01-01
    SRCFMT = Unknown - Automatic Detection
    -> AttributeValueMapper
    -> NullAttributeMapper
Note: Oversetter medium fra initialverdier til kodetekst
AttributeValueMapper [off]
    DEFAULT_VALUE = _FME_NO_OP_
    DIRECTION = Forward (Source To Destination)
    LUT = B,iBygning,D,tidvisUnderVann,I,påIsbre,J,underIsbre,L,iLuft,O,påVannoverflaten,S,påSjøbunnen,T,påTerrenget,U,underTerrenget,V,alltidIVann,W,underSjøbunnen,X,ukjent
    SRC = medium
    VAL_ATTR = medium
    -> AttributeValueMapper_2 [off]
Note: Oversetter synbarhet fra initialverdier til kodetekst
AttributeValueMapper_2 [off]
    DEFAULT_VALUE = _FME_NO_OP_
    DIRECTION = Forward (Source To Destination)
    LUT = 0,fulltSynligOgGjenfinnbarITerrenget,1,dårligGjenfinnbarITerrenget,2,middelsSynligIFlybilde,3,dårligSynligIFlybilde
    SRC = kvalitet.Posisjonskvalitet.synbarhet
    VAL_ATTR = kvalitet.Posisjonskvalitet.synbarhet
    -> AttributeRemover
NullAttributeMapper
    ATTRCHOICE = Selected Attributes
    ATTRLIST = datafangstdato
    NEW_VALUE = 0001-01-01
    NULL_TREATMENT = New Value
    SOURCE_ATTR_VAL = Null Empty "Missing (Selected Attributes Only)"
    -> AttributeRemover
AttributeRemover
    LIST_ATTRS = lenke{}
    -> Veglenke (output)
Veglenke (output)
XMLFragmenter_2
    ATTRIBUTE_XML = _url_contents
    EMBEDDED_EXPRESSIONS = side/metadata
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = returnert neste.href
    REJECT_FEATURES_WITH_NO_FRAGMENTS = YES
    XML_SOURCE_TYPE = Attribute with XML document
    FRAGMENTS -> TestFilter
TestFilter
    DEFAULT_VALUE = <UNFILTERED>
    TEST_LIST = BOOL_OP,OR,COMPOSITE_TEST,<Unused>,TEST_CLAUSE,"TEST @Value(returnert) != 0",Flere
    Flere -> Loop (output)
Loop (output)

Bookmark: Lager unike noder
AttributeManager_2
    ATTR_TABLE = RENAME_SET_VALUE startnodeId > nodeId
    -> CoordinateExtractor_2
CoordinateExtractor_2
    IND = 0
    MODE = Specify Coordinate
    X_ATTR = _x
    Y_ATTR = _y
    Z_ATTR = _z
    -> AttributeKeeper
AttributeManager_3
    ATTR_TABLE = RENAME_SET_VALUE sluttnodeId > nodeId
    -> CoordinateExtractor
CoordinateExtractor
    IND = -1
    MODE = Specify Coordinate
    X_ATTR = _x
    Y_ATTR = _y
    Z_ATTR = _z
    -> AttributeKeeper
AttributeKeeper
    KEEP_ATTRS = _y,_x,identifikasjon.Identifikasjon.navnerom,nodeId,_z
    -> DuplicateFilter
DuplicateFilter
    INPUT_ORDERED_CHOICE = No
    KEYATTR = nodeId
    UNIQUE -> VertexCreator
Note: Lager nodepunkt
VertexCreator
    MODE_NAME = Replace with Point
    XVAL = @Value(_x)
    YVAL = @Value(_y)
    ZVAL = @Value(_z)
    -> GeometryPropertySetter_2
Note: Definerer geometriegenskap
GeometryPropertySetter_2
    GEOM_NAME_FIELD = posisjon
    OVERWRITE_CHOICE = Yes
    SETTYPE_PARAM = Geometry Name
    SET -> AttributeManager_4
Note: Lager nodeid
AttributeManager_4
    ATTR_TABLE:
      RENAME_SET_VALUE nodeId > identifikasjon.Identifikasjon.lokalId
      REMOVE _x
      REMOVE _y
      REMOVE _z
      SET_TO identifikasjon.Identifikasjon.navnerom = $(namespace).rn
      SET_TO gml_id = $(namespace).rn.@Value(identifikasjon.Identifikasjon.lokalId)
      SET_TO fme_feature_type = Vegnode
    -> Vegnode (output)
Vegnode (output)
